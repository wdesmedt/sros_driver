TIMETRA-MLD-MIB DEFINITIONS ::= BEGIN

IMPORTS
        MODULE-IDENTITY,
        OBJECT-TYPE, Unsigned32, Counter32, 
        Gauge32, NOTIFICATION-TYPE, Integer32            FROM SNMPv2-SMI

        MODULE-COMPLIANCE, OBJECT-GROUP,                 
        NOTIFICATION-GROUP                              FROM SNMPv2-CONF

        RowStatus, TimeStamp, TruthValue,
        TimeInterval, MacAddress,
        DisplayString                                   FROM SNMPv2-TC

        timetraSRMIBModules, tmnxSRObjs, 
        tmnxSRNotifyPrefix, tmnxSRConfs                 FROM TIMETRA-GLOBAL-MIB

        InetAddressType, InetAddress                    FROM INET-ADDRESS-MIB 

        TmnxAdminState, 
        TmnxOperState,
        TPolicyStatementNameOrEmpty,
        TmnxMldVersion,
        TmnxServId,
        TmnxPppoeSessionId,
        TmnxSubIdentStringOrEmpty,
        TmnxMldGroupFilterMode,
        TmnxMldGroupType,
        TmnxVRtrID, TmnxVRtrIDOrZero                    FROM TIMETRA-TC-MIB

        vRtrID, vRtrIfIndex                             FROM TIMETRA-VRTR-MIB

        vRtrIfFwdSvcId, vRtrGrpIfIndex                  FROM TIMETRA-IGMP-MIB

        tmnxMcacLevelId,
        tmnxMcacLagPortsDown                            FROM TIMETRA-MCAST-CAC-MIB

        sapPortId, sapEncapValue                        FROM TIMETRA-SAP-MIB

        InterfaceIndex, InterfaceIndexOrZero            FROM IF-MIB
        ;

timetraMldMIBModule MODULE-IDENTITY
        LAST-UPDATED    "201601010000Z"
        ORGANIZATION    "Nokia"
        CONTACT-INFO
            "Nokia SROS Support
             Web: http://www.nokia.com"
        DESCRIPTION
            "This document is the SNMP MIB module to manage and provision
             the Multicast Listener Discovery (MLD) feature protocol
             for the Nokia SROS device.

             Copyright 2008-2016 Nokia. All rights reserved.
             Reproduction of this document is authorized on the condition that
             the foregoing copyright notice is included.

             This SNMP MIB module (Specification) embodies Nokia's
             proprietary intellectual property. Nokia retains all 
             title and ownership in the Specification, including any revisions.

             Nokia grants all interested parties a non-exclusive
             license to use and distribute an unmodified copy of this
             Specification in connection with management of Nokia
             products, and without fee, provided this copyright notice and 
             license appear on all copies.

             This Specification is supplied 'as is', and Nokia
             makes no warranty, either express or implied, as to the use,
             operation, condition, or performance of the Specification."

        REVISION     "201601010000Z"
        DESCRIPTION  "Rev 14.0               01 Jan 2016 00:00
                      14.0 release of the TIMETRA-MLD-MIB."

        REVISION     "201401010000Z"
        DESCRIPTION  "Rev 12.0               01 Jan 2014 00:00
                      12.0 release of the TIMETRA-MLD-MIB."

        REVISION     "200807010000Z"
        DESCRIPTION  "Rev 6.1                01 Jul 2008 00:00
                      6.1 release of the TIMETRA-MLD-MIB."

        REVISION     "200801010000Z"
        DESCRIPTION  "Rev 0.1                01 Jan 2008 00:00
                      Initial version of the TIMETRA-MLD-MIB."

        ::= { timetraSRMIBModules 46 }

--%%%%%%%%%%%%%%%%%%%%%%%%%%%%%%%%%%%%%%%%%%%%%%%%%%%%%%%%%%%%%%%%%%%%%%
--
--  Nokia 77x0 SR series MLD protocol extensions
--

tmnxMldObjs                OBJECT IDENTIFIER ::= { tmnxSRObjs 46 }
    vRtrMldProtocolObjs          OBJECT IDENTIFIER ::= { tmnxMldObjs 1 }
    vRtrMldIfObjs                OBJECT IDENTIFIER ::= { tmnxMldObjs 2 }
    vRtrMldNotificationObjs      OBJECT IDENTIFIER ::= { tmnxMldObjs 3 }
    vRtrMldHostObjs              OBJECT IDENTIFIER ::= { tmnxMldObjs 4 }
    vRtrMldGrpIfObjs             OBJECT IDENTIFIER ::= { tmnxMldObjs 5 }

tmnxMldConformance         OBJECT IDENTIFIER ::= { tmnxSRConfs 46 }

vRtrMldNotifyPrefix     OBJECT IDENTIFIER ::= { tmnxSRNotifyPrefix 46 }
    vRtrMldNotifications        OBJECT IDENTIFIER ::= { vRtrMldNotifyPrefix 0 }

--
-- Textual Conventions
--
MldGrpItfOperState ::= TEXTUAL-CONVENTION
    STATUS  current
    DESCRIPTION
        "The MldGrpItfOperState data type is an enumerated integer that describes
        the values used to identify the current operational state of an
        MLD Group Interface."
    SYNTAX  INTEGER {
                unknown (1),
                noMldOnGrpItf (2),
                grpItfDown (3),
                inService (4),
                notFwding (5)
                }

--
-- The MLD General Table
--

vRtrMldGeneralTableLastChanged OBJECT-TYPE
    SYNTAX       TimeStamp
    MAX-ACCESS   read-only
    STATUS       current
    DESCRIPTION
        "The value of vRtrMldGeneralTableLastChanged indicates the sysUpTime
         at the time of the last modification of an entry in the
         vRtrMldGeneralTable.

         If no changes were made to the table since the last re-initialization
         of the local network management subsystem, then this object
         contains a zero value."
    ::= { vRtrMldProtocolObjs 1 }

vRtrMldGeneralTable   OBJECT-TYPE
    SYNTAX      SEQUENCE OF VRtrMldGeneralEntry
    MAX-ACCESS  not-accessible
    STATUS      current
    DESCRIPTION
        "The vRtrMldGeneralTable contains objects for general control and
         management of the MLD protocol instance within a virtual router."
    ::= { vRtrMldProtocolObjs 2 }

vRtrMldGeneralEntry   OBJECT-TYPE
    SYNTAX      VRtrMldGeneralEntry
    MAX-ACCESS  not-accessible
    STATUS      current
    DESCRIPTION
        "Each row entry represents an instance of the MLD protocol running
         within a virtual router.  Entries in this table cannot be 
         created and deleted via SNMP SET operations.  An entry in this table
         is created by the agent when TIMETRA-VRTR-MIB::vRtrMldStatus in the 
         vRtrConfTable is set to 'create'.  The entry is destroyed when 
         vRtrMldStatus is set to 'delete'."
    INDEX { vRtrID }
    ::= { vRtrMldGeneralTable 1 }

VRtrMldGeneralEntry ::=    SEQUENCE {
    vRtrMldGenQueryInterval         Unsigned32,
    vRtrMldGenLastMembQueryIntvl    Unsigned32,
    vRtrMldGenQueryResponseIntvl    Unsigned32,
    vRtrMldGenRobustCount           Unsigned32,
    vRtrMldGenLastChange            TimeStamp,
    vRtrMldGenAdminState            TmnxAdminState,
    vRtrMldGenOperState             TmnxOperState,
    vRtrMldGenGrpIfQrySrcIpAddrType InetAddressType,   
    vRtrMldGenGrpIfQrySrcIpAddr     InetAddress   
}

vRtrMldGenQueryInterval OBJECT-TYPE
    SYNTAX     Unsigned32 (2..1024)
    UNITS      "seconds"
    MAX-ACCESS read-create
    STATUS     current
    DESCRIPTION
        "The value of vRtrMldGenQueryInterval specifies the frequency at 
         which the MLD Host-Query packets are transmitted."
    DEFVAL { 125 }
    ::= { vRtrMldGeneralEntry 1 }

vRtrMldGenLastMembQueryIntvl OBJECT-TYPE
    SYNTAX     Unsigned32 (1..1023)
    UNITS      "seconds"
    MAX-ACCESS read-create
    STATUS     current
    DESCRIPTION
        "The value of vRtrMldGenLastMembQueryIntvl specifies the Max Response 
         Time inserted into Group-Specific Queries sent in response to
         Leave Group messages, and is also the amount of time between
         Group-Specific Query messages.  This value may be tuned to
         modify the leave latency of the network.  A reduced value
         results in reduced time to detect the loss of the last
         member of a group."
    DEFVAL { 1 }
    ::= { vRtrMldGeneralEntry 2 }

vRtrMldGenQueryResponseIntvl OBJECT-TYPE
    SYNTAX     Unsigned32 (1..1023)
    UNITS      "seconds"
    MAX-ACCESS read-create
    STATUS     current
    DESCRIPTION
        "The value of vRtrMldGenQueryResponseIntvl specifies 
         maximum query response time advertised in Mldv2 queries."
    DEFVAL { 10 }
    ::= { vRtrMldGeneralEntry 3 }

vRtrMldGenRobustCount OBJECT-TYPE
    SYNTAX     Unsigned32 (2..10)
    MAX-ACCESS read-create
    STATUS     current
    DESCRIPTION
        "The value of vRtrMldGenRobustCount specifies the allowed tuning
         for the expected packet loss on a subnet. If a subnet is expected
         to be lossy, the Robustness Variable may be increased.  MLD is
         robust to (Robustness Variable-1) packet losses."
    DEFVAL { 2 }
    ::= { vRtrMldGeneralEntry 4 }

vRtrMldGenLastChange       OBJECT-TYPE
    SYNTAX      TimeStamp
    MAX-ACCESS  read-only
    STATUS      current
    DESCRIPTION
        "The value of vRtrMldGenLastChange indicates the sysUpTime 
         when this row was last modified."
    ::= { vRtrMldGeneralEntry 5 }

vRtrMldGenAdminState   OBJECT-TYPE
    SYNTAX      TmnxAdminState
    MAX-ACCESS  read-create
    STATUS      current
    DESCRIPTION
        "The value of vRtrMldGenAdminState specifies the current administrative 
         state of the MLD protocol instance on this virtual router.

         When vRtrMldGenAdminState is set to 'inService', the agent
         attempts to enable the MLD protocol instance on this virtual router.
             
         When vRtrMldGenAdminState is set to 'outOfService', the
         agent attempts to disable the MLD protocol instance on this
         router."
    DEFVAL { inService }
    ::= { vRtrMldGeneralEntry 6 }
                   
vRtrMldGenOperState    OBJECT-TYPE
    SYNTAX      TmnxOperState
    MAX-ACCESS  read-only
    STATUS      current
    DESCRIPTION
        "The value of vRtrMldGenOperState indicates the current operating state
         of this MLD protocol instance on this router."
    ::= { vRtrMldGeneralEntry 7 }

vRtrMldGenGrpIfQrySrcIpAddrType OBJECT-TYPE
    SYNTAX     InetAddressType
    MAX-ACCESS read-create
    STATUS     current
    DESCRIPTION
        "The value of vRtrMldGenGrpIfQrySrcIpAddrType indicates the type of 
         address to be used for vRtrMldGenGrpIfQrySrcIpAddr."         
    ::= { vRtrMldGeneralEntry 8 }

vRtrMldGenGrpIfQrySrcIpAddr OBJECT-TYPE
    SYNTAX     InetAddress (SIZE(0|16))
    MAX-ACCESS read-create
    STATUS     current
    DESCRIPTION
        "The value of vRtrMldGenGrpIfQrySrcIpAddr specifies the source IP  
         address used when generating MLD queries on group interfaces."
    ::= { vRtrMldGeneralEntry 9 }


--
--  The MLD Source Group Global Database
--

vRtrMldGrpSrcTable OBJECT-TYPE
    SYNTAX     SEQUENCE OF VRtrMldGrpSrcEntry
    MAX-ACCESS not-accessible
    STATUS     current
    DESCRIPTION
        "The vRtrMldGrpSrcTable lists the IP multicast sources 
         corresponding to the IP multicast groups. This table represents 
         the global MLD source, group database."
    ::= { vRtrMldProtocolObjs 3 }

vRtrMldGrpSrcEntry OBJECT-TYPE
    SYNTAX     VRtrMldGrpSrcEntry
    MAX-ACCESS not-accessible
    STATUS     current
    DESCRIPTION
        "An entry in the vRtrMldGrpSrcTable. Each entry represents a source 
         address from which receivers are interested or not interested in 
         receiving multicast traffic."
    INDEX      { vRtrID,
                 vRtrMldGrpSrcGroupAddrType,
                 vRtrMldGrpSrcGroupAddress, 
                 vRtrMldGrpSrcSourceAddrType,
                 vRtrMldGrpSrcSourceAddress, 
                 vRtrMldGrpSrcFwdOrBlk, 
                 vRtrIfIndex }
    ::= { vRtrMldGrpSrcTable 1 }

VRtrMldGrpSrcEntry ::= SEQUENCE {
    vRtrMldGrpSrcGroupAddrType      InetAddressType,
    vRtrMldGrpSrcGroupAddress       InetAddress,
    vRtrMldGrpSrcSourceAddrType     InetAddressType,
    vRtrMldGrpSrcSourceAddress      InetAddress,
    vRtrMldGrpSrcFwdOrBlk           INTEGER,
    vRtrMldGrpSrcUpTime             Unsigned32
}

vRtrMldGrpSrcGroupAddrType OBJECT-TYPE
    SYNTAX     InetAddressType
    MAX-ACCESS not-accessible
    STATUS     current
    DESCRIPTION
        "The value of vRtrMldGrpSrcGroupAddrType indicates the type of 
         address to be used for IP multicast group address."         
    ::= { vRtrMldGrpSrcEntry 1 }

vRtrMldGrpSrcGroupAddress OBJECT-TYPE
    SYNTAX     InetAddress (SIZE(16))
    MAX-ACCESS not-accessible
    STATUS     current
    DESCRIPTION
        "The value of vRtrMldGrpSrcGroupAddress indicates the IP multicast 
         group address for which this entry contains information."
    ::= { vRtrMldGrpSrcEntry 2 }

vRtrMldGrpSrcSourceAddrType OBJECT-TYPE
    SYNTAX     InetAddressType
    MAX-ACCESS not-accessible
    STATUS     current
    DESCRIPTION
        "The value of vRtrMldGrpSrcSourceAddrType indicates the type of 
         address to be used for source address."
    ::= { vRtrMldGrpSrcEntry 3 }

vRtrMldGrpSrcSourceAddress OBJECT-TYPE
    SYNTAX     InetAddress (SIZE(16))
    MAX-ACCESS not-accessible
    STATUS     current
    DESCRIPTION
        "The value of vRtrMldGrpSrcSourceAddress indicates the source address 
         for which this entry contains information."
    ::= { vRtrMldGrpSrcEntry 4 }

vRtrMldGrpSrcFwdOrBlk OBJECT-TYPE
    SYNTAX     INTEGER {
                   forward (1),
                   block (2)
               }
    MAX-ACCESS not-accessible
    STATUS     current
    DESCRIPTION
        "The value of vRtrMldGrpSrcFwdOrBlk indicates whether this entry is 
         on the forward list or block list."
    ::= { vRtrMldGrpSrcEntry 5 }

vRtrMldGrpSrcUpTime    OBJECT-TYPE
    SYNTAX      Unsigned32
    UNITS       "seconds"
    MAX-ACCESS  read-only
    STATUS      current
    DESCRIPTION
        "The value of vRtrMldGrpSrcUpTime indicates the time since 
         this source group entry was created."
    ::= { vRtrMldGrpSrcEntry 6 }


--
--  The MLD Source Specific Multicast (SSM) Translate Table
--

vRtrMldSsmTransTableLastChanged OBJECT-TYPE
    SYNTAX       TimeStamp
    MAX-ACCESS   read-only
    STATUS       current
    DESCRIPTION
        "The value of vRtrMldSsmTransTableLastChanged indicates the
         sysUpTime value at the time of the last modification of an entry
         in the vRtrMldSsmTransTable.
        
         If no changes were made to the table since the last re-initialization
         of the local network management subsystem, then this object
         contains a zero value."
    ::= { vRtrMldProtocolObjs 4 }

vRtrMldSsmTransTable OBJECT-TYPE
    SYNTAX     SEQUENCE OF VRtrMldSsmTransEntry
    MAX-ACCESS not-accessible
    STATUS     current
    DESCRIPTION
        "The vRtrMldSsmTransTable is used to configure group ranges which
         are translated to SSM (S,G) entries."
    ::= { vRtrMldProtocolObjs 5 }

vRtrMldSsmTransEntry OBJECT-TYPE
    SYNTAX     VRtrMldSsmTransEntry
    MAX-ACCESS not-accessible
    STATUS     current
    DESCRIPTION
        "An entry in the vRtrMldSsmTransTable. Entries can         
         be created or deleted by an SNMP SET request to 
         vRtrMldSsmTransRowStatus."
    INDEX      { vRtrID, 
                 vRtrMldSsmTransGrpAddrType1,
                 vRtrMldSsmTransGrpAddr1,
                 vRtrMldSsmTransGrpAddrType2, 
                 vRtrMldSsmTransGrpAddr2,
                 vRtrMldSsmTransSrcAddrType, 
                 vRtrMldSsmTransSrcAddr }
    ::= { vRtrMldSsmTransTable 1 }

VRtrMldSsmTransEntry ::= SEQUENCE {
    vRtrMldSsmTransGrpAddrType1  InetAddressType, 
    vRtrMldSsmTransGrpAddr1      InetAddress,
    vRtrMldSsmTransGrpAddrType2  InetAddressType,    
    vRtrMldSsmTransGrpAddr2      InetAddress,
    vRtrMldSsmTransSrcAddrType   InetAddressType,
    vRtrMldSsmTransSrcAddr       InetAddress,
    vRtrMldSsmTransRowStatus     RowStatus,
    vRtrMldSsmTransLastChanged   TimeStamp
}

vRtrMldSsmTransGrpAddrType1 OBJECT-TYPE
    SYNTAX     InetAddressType
    MAX-ACCESS not-accessible
    STATUS     current
    DESCRIPTION
        "The value of vRtrMldSsmTransGrpAddrType1 indicates the starting 
         address type of the group range."
    ::= { vRtrMldSsmTransEntry 1 }

vRtrMldSsmTransGrpAddr1 OBJECT-TYPE
    SYNTAX     InetAddress (SIZE(16))
    MAX-ACCESS not-accessible
    STATUS     current
    DESCRIPTION
        "The value of vRtrMldSsmTransGrpAddr1 indicates the start of 
         the group range."
    ::= { vRtrMldSsmTransEntry 2 }

vRtrMldSsmTransGrpAddrType2 OBJECT-TYPE
    SYNTAX     InetAddressType
    MAX-ACCESS not-accessible
    STATUS     current
    DESCRIPTION
        "The value of vRtrMldSsmTransGrpAddrType2 indicates the ending 
         address type of the group range."
    ::= { vRtrMldSsmTransEntry 3 }

vRtrMldSsmTransGrpAddr2 OBJECT-TYPE
    SYNTAX     InetAddress (SIZE(16))
    MAX-ACCESS not-accessible
    STATUS     current
    DESCRIPTION
        "The value of vRtrMldSsmTransGrpAddr2 indicates the end 
         of the group range."
    ::= { vRtrMldSsmTransEntry 4 }

vRtrMldSsmTransSrcAddrType OBJECT-TYPE
    SYNTAX     InetAddressType
    MAX-ACCESS not-accessible
    STATUS     current 
    DESCRIPTION
        "The value of vRtrMldSsmTransSrcAddrType indicates the type of 
         the source address for this group range."
    ::= { vRtrMldSsmTransEntry 5 }

vRtrMldSsmTransSrcAddr OBJECT-TYPE
    SYNTAX     InetAddress (SIZE(16))
    MAX-ACCESS not-accessible
    STATUS     current
    DESCRIPTION
        "The value of vRtrMldSsmTransSrcAddr indicates
         the source address for this group range. Whenever a (*,G) report is
         received in the range specified by vRtrMldSsmTransGrpAddr1 and
         vRtrMldSsmTransGrpAddr2, it is translated to an (S,G) report
         with the value of this object as the source address."
    ::= { vRtrMldSsmTransEntry 6 }

vRtrMldSsmTransRowStatus OBJECT-TYPE
    SYNTAX     RowStatus
    MAX-ACCESS read-create
    STATUS     current
    DESCRIPTION
        "The value of vRtrMldSsmTransRowStatus is used to 
         create or delete an entry in this table."
    ::= { vRtrMldSsmTransEntry 7 }

vRtrMldSsmTransLastChanged OBJECT-TYPE
    SYNTAX     TimeStamp
    MAX-ACCESS read-only
    STATUS     current
    DESCRIPTION
        "The value of vRtrMldSsmTransLastChanged indicates the sysUpTime 
         when this row was last modified."
    ::= { vRtrMldSsmTransEntry 8 }

--
-- The MLD General Statistics Table
--

vRtrMldGenStatsTable   OBJECT-TYPE
    SYNTAX      SEQUENCE OF VRtrMldGenStatsEntry
    MAX-ACCESS  not-accessible
    STATUS      current
    DESCRIPTION
        "The vRtrMldGenStatsTable contains objects for general statistics  
        for the MLD protocol instance within a virtual router."
    ::= { vRtrMldProtocolObjs 6 }

vRtrMldGenStatsEntry   OBJECT-TYPE
    SYNTAX      VRtrMldGenStatsEntry
    MAX-ACCESS  not-accessible
    STATUS      current
    DESCRIPTION
        "Each row entry represents statistics for an instance of the 
         MLD protocol running within a virtual router."
    AUGMENTS      { vRtrMldGeneralEntry }
    ::= { vRtrMldGenStatsTable 1 }

VRtrMldGenStatsEntry ::=    SEQUENCE {
    vRtrMldGenStatsStarGTypes       Gauge32,
    vRtrMldGenStatsSGTypes          Gauge32
}

vRtrMldGenStatsStarGTypes OBJECT-TYPE
    SYNTAX       Gauge32
    MAX-ACCESS   read-only
    STATUS       current
    DESCRIPTION
        "The value of vRtrMldGenStatsStarGTypes indicates the number of 
         entries in vRtrMldGrpSrcTable for which the source type is 'starG'."
    ::= { vRtrMldGenStatsEntry 1 }

vRtrMldGenStatsSGTypes OBJECT-TYPE
    SYNTAX       Gauge32
    MAX-ACCESS   read-only
    STATUS       current
    DESCRIPTION
        "The value of vRtrMldGenStatsSGTypes indicates the number of entries in
         vRtrMldGrpSrcTable for which the source type is 'sg'."
    ::= { vRtrMldGenStatsEntry 2 }

--
--  The MLD Interface Table
--

vRtrMldIfTableLastChanged OBJECT-TYPE
    SYNTAX       TimeStamp
    MAX-ACCESS   read-only
    STATUS       current
    DESCRIPTION
        "The value of vRtrMldIfTableLastChanged indicates the sysUpTime
         at the time of the last modification of an entry in the
         vRtrMldIfTable.

         If no changes were made to the table since the last re-initialization
         of the local network management subsystem, then this object
         contains a zero value."
    ::= { vRtrMldIfObjs 1 }

vRtrMldIfTable OBJECT-TYPE
    SYNTAX     SEQUENCE OF VRtrMldIfEntry
    MAX-ACCESS not-accessible
    STATUS     current
    DESCRIPTION
        "The vRtrMldIfTable contains objects corresponding to the 
         interfaces on which the MLD protocol operation is enabled."
    ::= { vRtrMldIfObjs 2 }

vRtrMldIfEntry OBJECT-TYPE
    SYNTAX     VRtrMldIfEntry
    MAX-ACCESS not-accessible
    STATUS     current
    DESCRIPTION
        "Each row entry in the vRtrMldIfTable represents an interface on
         this router that participates in the MLD protocol.  An entry in
         this table can be created or destroyed by an SNMP SET request to
         vRtrMldIfRowStatus.  An attempt to destroy a row will fail if
         vRtrMldIfAdminState has not first been set to 'outOfService'."
    INDEX      { vRtrID, 
                 vRtrIfIndex }
    ::= { vRtrMldIfTable 1 }

VRtrMldIfEntry ::= SEQUENCE {
    vRtrMldIfRowStatus             RowStatus,
    vRtrMldIfLastChanged           TimeStamp,
    vRtrMldIfAdminState            TmnxAdminState,
    vRtrMldIfOperState             TmnxOperState,
    vRtrMldIfAdminVersion          TmnxMldVersion,
    vRtrMldIfOperVersion           TmnxMldVersion,
    vRtrMldIfQuerierType           InetAddressType,
    vRtrMldIfQuerier               InetAddress,
    vRtrMldIfImportPolicy          TPolicyStatementNameOrEmpty,
    vRtrMldIfGroupCount            Gauge32,
    vRtrMldIfQuerierUpTime         Unsigned32,
    vRtrMldIfQuerierExpiryTime     Unsigned32,
    vRtrMldIfNextGenQueryTime      Unsigned32,
    vRtrMldIfMaxGroups             Unsigned32,
    vRtrMldIfMaxGroupsTillNow      Counter32,
    vRtrMldIfQueryInterval         Unsigned32,
    vRtrMldIfLastMembQueryIntvl    Unsigned32,
    vRtrMldIfQueryResponseIntvl    Unsigned32,
    vRtrMldIfDisRtrAlertChk        TruthValue,
    vRtrMldIfMcacPolicyName        TPolicyStatementNameOrEmpty,
    vRtrMldIfMcacUnconstrainedBW   Integer32,
    vRtrMldIfMcacConstAdminState   TmnxAdminState,
    vRtrMldIfMcacPreRsvdMandBW     Integer32,
    vRtrMldIfMcacinUseMandBw       Unsigned32, 
    vRtrMldIfMcacinUseOpnlBw       Unsigned32, 
    vRtrMldIfMcacAvailMandBw       Unsigned32, 
    vRtrMldIfMcacAvailOpnlBw       Unsigned32,
    vRtrMldIfMcacValuesInTransit   TruthValue,
    vRtrMldIfMaxSources            Unsigned32,
    vRtrMldIfMaxGrpSources         Unsigned32,
    vRtrMldIfMcacUseLagPortWeight  TruthValue,
    vRtrMldIfMcacIfPolicyName           TPolicyStatementNameOrEmpty
}

vRtrMldIfRowStatus OBJECT-TYPE
    SYNTAX     RowStatus
    MAX-ACCESS read-create
    STATUS     current
    DESCRIPTION
        "The value of vRtrMldIfRowStatus is used to 
         create or delete an entry in this table.
         
         The activation of a row enables the MLD on the interface. The
         destruction of a row disables the MLD on the interface. Before 
         this row can be destroyed, vRtrMldIfAdminState must have been 
         set to 'outOfService'."
    ::= { vRtrMldIfEntry 1 }

vRtrMldIfLastChanged       OBJECT-TYPE
    SYNTAX      TimeStamp
    MAX-ACCESS  read-only
    STATUS      current
    DESCRIPTION
        "The value of vRtrMldIfLastChanged indicates 
         the sysUpTime when this row was last modified."
    ::= { vRtrMldIfEntry 2 }

vRtrMldIfAdminState       OBJECT-TYPE
    SYNTAX      TmnxAdminState
    MAX-ACCESS  read-create
    STATUS      current
    DESCRIPTION
        "The value of vRtrMldIfAdminState specifies the desired 
         administrative state for the MLD protocol on this interface."
    DEFVAL { inService }
    ::= { vRtrMldIfEntry 3 }

vRtrMldIfOperState        OBJECT-TYPE
    SYNTAX      TmnxOperState
    MAX-ACCESS  read-only
    STATUS      current
    DESCRIPTION
        "The value of vRtrMldIfOperState indicates the current operational 
         state of the MLD protocol on this interface."
    ::= { vRtrMldIfEntry 4 }

vRtrMldIfAdminVersion OBJECT-TYPE
    SYNTAX     TmnxMldVersion
    MAX-ACCESS read-create
    STATUS     current
    DESCRIPTION
        "The value of vRtrMldIfAdminVersion specifies the configured version 
         of the MLD which is running on this interface.
         
         This object can be used to configure a router capable of
         running either value.  For the MLD to function correctly, all
         routers on a LAN must be configured to run the same version
         of the MLD on that LAN."
    DEFVAL { version2 }
    ::= { vRtrMldIfEntry 5 }

vRtrMldIfOperVersion OBJECT-TYPE
    SYNTAX     TmnxMldVersion
    MAX-ACCESS read-only
    STATUS     current
    DESCRIPTION
        "The value of vRtrMldIfOperVersion indicates the operational version 
         of the MLD which is running on this interface."
    ::= { vRtrMldIfEntry 6 }

vRtrMldIfQuerierType OBJECT-TYPE
    SYNTAX     InetAddressType
    MAX-ACCESS read-only
    STATUS     current
    DESCRIPTION
        "The value of vRtrMldIfQuerierType indicates the type of address of 
         the MLD Querier on the IP subnet to which this interface is attached."
    ::= { vRtrMldIfEntry 7 }

vRtrMldIfQuerier OBJECT-TYPE
    SYNTAX     InetAddress (SIZE(0|16))
    MAX-ACCESS read-only
    STATUS     current
    DESCRIPTION
        "The value of vRtrMldIfQuerier indicates the address of the MLD Querier 
         on the IP subnet to which this interface is attached."
    ::= { vRtrMldIfEntry 8 }

vRtrMldIfImportPolicy OBJECT-TYPE
    SYNTAX     TPolicyStatementNameOrEmpty
    MAX-ACCESS read-create
    STATUS     current
    DESCRIPTION
        "The value of vRtrMldIfImportPolicy specifies the policy 
         that is to be applied on this interface."
    DEFVAL { ''H }
    ::= { vRtrMldIfEntry 9 }

vRtrMldIfGroupCount OBJECT-TYPE
    SYNTAX     Gauge32
    MAX-ACCESS read-only
    STATUS     current
    DESCRIPTION
        "The value of vRtrMldIfGroupCount indicates the number of multicast 
         groups which have been learned by the router on this interface."
    ::= { vRtrMldIfEntry 10 }

vRtrMldIfQuerierUpTime OBJECT-TYPE
    SYNTAX     Unsigned32
    UNITS      "seconds"
    MAX-ACCESS read-only
    STATUS     current
    DESCRIPTION
        "The value of vRtrMldIfQuerierUpTime indicates the time since 
         vRtrMldIfQuerier was last elected as querier."
    ::= { vRtrMldIfEntry 11 }

vRtrMldIfQuerierExpiryTime OBJECT-TYPE
    SYNTAX     Unsigned32
    UNITS      "seconds"
    MAX-ACCESS read-only
    STATUS     current
    DESCRIPTION
        "The value of vRtrMldIfQuerierExpiryTime indicates the time remaining 
         before vRtrMldIfQuerier is aged out. If vRtrMldIfQuerier is the local
         interface address, the value of vRtrMldIfQuerierExpiryTime
         will be zero."
    ::= { vRtrMldIfEntry 12 }

vRtrMldIfNextGenQueryTime OBJECT-TYPE
    SYNTAX     Unsigned32
    UNITS      "seconds"
    MAX-ACCESS read-only
    STATUS     current
    DESCRIPTION
        "The value of vRtrMldIfNextGenQueryTime indicates the 
         time remaining before the general query is sent on this interface
         if this router is the querier(vRtrMldIfQuerier is a 
         local address).

         If this router is not the querier on the interface, the value
         of this object will be zero."
    ::= { vRtrMldIfEntry 13 }

vRtrMldIfMaxGroups OBJECT-TYPE
    SYNTAX     Unsigned32 (0|1..16000)
    MAX-ACCESS read-create
    STATUS     current
    DESCRIPTION
        "The value of vRtrMldIfMaxGroups specifies the maximum number of groups
         for which the MLD can have local receiver information based on received
         MLD reports on this interface.  When this configuration is changed 
         dynamically to a value lower than currently accepted number of groups,
         the groups that are already accepted are not deleted.  Only new groups 
         will not be allowed.  When this object has a value of 0, there is no 
         limit to the number of groups."
    DEFVAL { 0 }
    ::= { vRtrMldIfEntry 14 }

vRtrMldIfMaxGroupsTillNow OBJECT-TYPE
    SYNTAX     Counter32
    MAX-ACCESS read-only
    STATUS     current
    DESCRIPTION
        "The value of vRtrMldIfMaxGroupsTillNow indicates the highest value 
         that vRtrMldIfMaxGroups had till now.

         If the value of vRtrMldIfMaxGroups is set to 0, the value of 
         vRtrMldIfMaxGroupsTillNow is 0, which means there is no limit to
         the number of groups till now."
    ::= { vRtrMldIfEntry 15 }

vRtrMldIfQueryInterval OBJECT-TYPE
    SYNTAX     Unsigned32 (0 | 2..1024)
    UNITS      "seconds"
    MAX-ACCESS read-create
    STATUS     current
    DESCRIPTION
        "The value of vRtrMldIfQueryInterval specifies the frequency at 
         which the MLD Host-Query packets are transmitted on this interface."
    DEFVAL { 0 }
    ::= { vRtrMldIfEntry 16 }

vRtrMldIfLastMembQueryIntvl OBJECT-TYPE
    SYNTAX     Unsigned32 (0 | 1..1023)
    UNITS      "seconds"
    MAX-ACCESS read-create
    STATUS     current
    DESCRIPTION
        "The value of vRtrMldIfLastMembQueryIntvl specifies the Max Response 
         Time inserted into Group-Specific Queries sent in response to
         Leave Group messages, and is also the amount of time between
         Group-Specific Query messages.  This value may be tuned to
         modify the leave latency of the network.  A reduced value
         results in reduced time to detect the loss of the last
         member of a group."
    DEFVAL { 0 }
    ::= { vRtrMldIfEntry 17 }

vRtrMldIfQueryResponseIntvl OBJECT-TYPE
    SYNTAX     Unsigned32 (0 | 1..1023)
    UNITS      "seconds"
    MAX-ACCESS read-create
    STATUS     current
    DESCRIPTION
        "The value of vRtrMldIfQueryResponseIntvl specifies 
         maximum query response time advertised in Mldv2 queries
         on this interface."
    DEFVAL { 0 }
    ::= { vRtrMldIfEntry 18 }

vRtrMldIfDisRtrAlertChk OBJECT-TYPE
    SYNTAX     TruthValue
    MAX-ACCESS read-create
    STATUS     current
    DESCRIPTION
        "vRtrMldIfDisRtrAlertChk is used to enable/disable router
         alert checking for MLD messages received on this interface.

         If this flag is set to 'true', checking is disabled." 
    DEFVAL     { false }
    ::= { vRtrMldIfEntry 19 }

vRtrMldIfMcacPolicyName OBJECT-TYPE
    SYNTAX     TPolicyStatementNameOrEmpty
    MAX-ACCESS read-create
    STATUS     current
    DESCRIPTION
        "The value of vRtrMldIfMcacPolicyName specifies the name 
         of the multicast CAC policy.

         The multicast cac policy applies the interface cac algorithm if 
         the channel(group) on this interface is part of the policy as specified
         in vRtrMldIfMcacPolicyName."
    DEFVAL { "" }
    ::= { vRtrMldIfEntry 20 }

vRtrMldIfMcacUnconstrainedBW OBJECT-TYPE
    SYNTAX      Integer32 (-1|0..2147483647)
    UNITS       "kbps"
    MAX-ACCESS  read-create
    STATUS      current
    DESCRIPTION
        "The value of vRtrMldIfMcacUnconstrainedBW specifies the bandwidth assigned
         for interface's multicast cac policy traffic in kilo-bits per 
         second(kbps). 
         
         If the default value of '-1' is set, there is no constraint on bandwidth 
         allocated at the interface. 
         
         If the value of vRtrMldIfMcacUnconstrainedBW is set to '0' and if 
         a multicast cac policy is assigned on the interface, then 
         no group (channel) from that policy is allowed on that interface."
    DEFVAL { -1 }
    ::= { vRtrMldIfEntry 21 }

vRtrMldIfMcacConstAdminState OBJECT-TYPE
    SYNTAX      TmnxAdminState
    MAX-ACCESS  read-create
    STATUS      current
    DESCRIPTION
        "The value of vRtrMldIfMcacConstAdminState specifies the 
         administrative state of the multicast CAC policy's constraints."
    DEFVAL { inService } 
    ::= { vRtrMldIfEntry 22 }

vRtrMldIfMcacPreRsvdMandBW OBJECT-TYPE
    SYNTAX      Integer32 (-1|0..2147483647)
    UNITS       "kbps"
    MAX-ACCESS  read-create
    STATUS      current
    DESCRIPTION
        "The value of vRtrMldIfMcacPreRsvdMandBW specifies the bandwidth
         pre-reserved for all the mandatory channels on a given interface
         in kilo-bits per second(kbps). 
              
         If the value of vRtrMldIfMcacUnconstrainedBW is '0', no mandatory
         channels are allowed. If the value of vRtrMldIfMcacUnconstrainedBW 
         is '-1', then all mandatory and optional channels are allowed.

         If the value of vRtrMldIfMcacPreRsvdMandBW is equal to the value of
         vRtrMldIfMcacUnconstrainedBW, then all the unconstrained bandwidth
         on a given interface is allocated to mandatory channels configured 
         through multicast cac policy on that interface and no optional 
         groups (channels) are allowed.

         The value of vRtrMldIfMcacPreRsvdMandBW should always be less than
         or equal to that of vRtrMldIfMcacUnconstrainedBW. An attempt to set
         the value of vRtrMldIfMcacPreRsvdMandBW greater than that of 
         vRtrMldIfMcacUnconstrainedBW will result in inconsistent value error."
    DEFVAL { -1 }
    ::= { vRtrMldIfEntry 23 }

vRtrMldIfMcacinUseMandBw  OBJECT-TYPE
    SYNTAX     Unsigned32
    UNITS      "kbps"
    MAX-ACCESS read-only
    STATUS     current
    DESCRIPTION
        "The value of vRtrMldIfMcacinUseMandBw indicates the 
         in-use bandwidth in kilo-bits per second(kbps) for the 
         mandatory channels for this protocol interface instance."
    ::= { vRtrMldIfEntry 24 }

vRtrMldIfMcacinUseOpnlBw  OBJECT-TYPE
    SYNTAX     Unsigned32
    UNITS      "kbps"
    MAX-ACCESS read-only
    STATUS     current
    DESCRIPTION
        "The value of vRtrMldIfMcacinUseOpnlBw indicates the 
         in-use bandwidth in kilo-bits per second(kbps) for the 
         optional channels for this protocol interface instance."
    ::= { vRtrMldIfEntry 25 }

vRtrMldIfMcacAvailMandBw  OBJECT-TYPE
    SYNTAX     Unsigned32
    UNITS      "kbps"
    MAX-ACCESS read-only
    STATUS     current
    DESCRIPTION
        "The value of vRtrMldIfMcacAvailMandBw indicates the 
         pre-reserved bandwidth in kilo-bits per second(kbps) 
         for the mandatory channels for this interface instance."
    ::= { vRtrMldIfEntry 26 }

vRtrMldIfMcacAvailOpnlBw  OBJECT-TYPE
    SYNTAX     Unsigned32
    UNITS      "kbps"
    MAX-ACCESS read-only
    STATUS     current
    DESCRIPTION
        "The value of vRtrMldIfMcacAvailOpnlBw indicates the 
         available bandwidth in kilo-bits per second(kbps) for this 
         interface instance."
    ::= { vRtrMldIfEntry 27 }

vRtrMldIfMcacValuesInTransit   OBJECT-TYPE
    SYNTAX      TruthValue
    MAX-ACCESS  read-only
    STATUS      current
    DESCRIPTION
        "The value of vRtrMldIfMcacValuesInTransit indicates that the
         operational (available and in-use mandatory/optional) value for the 
         following objects are in transition due to configuration change:

         vRtrMldIfMcacAvailMandBw
         vRtrMldIfMcacAvailOpnlBw
         vRtrMldIfMcacinUseMandBw
         vRtrMldIfMcacinUseOpnlBw

         When Multicast CAC Policy is applied on the interface for the join
         of the next channel, the operational values will be recalculated and 
         applied to the above objects and the value for vRtrMldIfMcacValuesInTransit
         will be set to 'false'.

         If the value of vRtrMldIfMcacValuesInTransit is 'true' then the values 
         are in transition."
    ::= { vRtrMldIfEntry 28 }

vRtrMldIfMaxSources OBJECT-TYPE
    SYNTAX     Unsigned32 (0|1..1000)
    MAX-ACCESS read-create
    STATUS     current
    DESCRIPTION
        "The value of vRtrMldIfMaxSources specifies the maximum number of sources
         for which Mld can have local receiver information based on received
         Mld reports on this interface.  When this configuration is changed 
         dynamically to a value lower than currently accepted number of sources,
         the sources that are already accepted are not deleted. Only new sources 
         will not be allowed. When this object has a value of 0, there is no 
         limit to the number of sources."
    DEFVAL { 0 }
    ::= { vRtrMldIfEntry 29 }

vRtrMldIfMaxGrpSources OBJECT-TYPE
    SYNTAX     Unsigned32 (0|1..32000)
    MAX-ACCESS read-create
    STATUS     current
    DESCRIPTION
        "The value of vRtrMldIfMaxGrpSources specifies the maximum number of
         group sources for which MLD can have local receiver information based 
         on received MLD reports on this interface.  When this configuration is 
         changed dynamically to a value lower than currently accepted number of
         group sources, the group sources that are already accepted are not 
         deleted. Only new group sources will not be allowed. When this object
         has a value of 0, there is no limit to the number of group sources."
    DEFVAL { 0 }
    ::= { vRtrMldIfEntry 30 }    
    
vRtrMldIfMcacUseLagPortWeight OBJECT-TYPE
    SYNTAX     TruthValue
    MAX-ACCESS read-create
    STATUS     current
    DESCRIPTION
        "The value of vRtrMldIfMcacUseLagPortWeight specifies
         if this system must use the LAG port weight
         while calculating Multicast CAC constraints.
         
         The LAG port weight is configured with the 
         object TIMETRA-LAG-MIB::tLagPortWeightSpeed."
    DEFVAL { false }
    ::= { vRtrMldIfEntry 31 }

vRtrMldIfMcacIfPolicyName OBJECT-TYPE
    SYNTAX     TPolicyStatementNameOrEmpty
    MAX-ACCESS read-create
    STATUS     current
    DESCRIPTION
        "The value of vRtrMldIfMcacIfPolicyName specifies the name 
         of the multicast CAC interface-policy.

         The multicast cac policy applies the interface cac algorithm if 
         the channel(group) on this interface is part of the policy as specified
         in vRtrMldIfMcacIfPolicyName."
    DEFVAL { "" }
    ::= { vRtrMldIfEntry 32 }

--
--  The MLD Interface Group Table
--

vRtrMldIfGroupTable OBJECT-TYPE
    SYNTAX     SEQUENCE OF VRtrMldIfGroupEntry
    MAX-ACCESS not-accessible
    STATUS     current
    DESCRIPTION
        "The vRtrMldIfGroupTable contains objects for the 
         IP multicast groups for which there are members 
         on a particular interface. This table represents 
         the MLD group database."
    ::= { vRtrMldIfObjs 3 }

vRtrMldIfGroupEntry OBJECT-TYPE
    SYNTAX     VRtrMldIfGroupEntry
    MAX-ACCESS not-accessible
    STATUS     current
    DESCRIPTION
        "An entry in the vRtrMldIfGroupTable. Each entry represents a 
         group address for which receivers are interested or not interested in 
         receiving multicast traffic."
    INDEX      { vRtrID, 
                 vRtrIfIndex,
                 vRtrMldIfGroupAddressType, 
                 vRtrMldIfGroupAddress }
    ::= { vRtrMldIfGroupTable 1 }

VRtrMldIfGroupEntry ::= SEQUENCE {
    vRtrMldIfGroupAddressType      InetAddressType, 
    vRtrMldIfGroupAddress          InetAddress,
    vRtrMldIfGroupType             INTEGER,
    vRtrMldIfGroupUpTime           TimeInterval,
    vRtrMldIfGroupExpiryTime       TimeInterval,
    vRtrMldIfGroupVer1HostTimer    TimeInterval,
    vRtrMldIfGroupMode             INTEGER,
    vRtrMldIfGroupCompatMode       TmnxMldVersion,
    vRtrMldIfGroupLstRprtrType     InetAddressType,
    vRtrMldIfGroupLastReporter     InetAddress
}

vRtrMldIfGroupAddressType OBJECT-TYPE
    SYNTAX     InetAddressType
    MAX-ACCESS not-accessible
    STATUS     current
    DESCRIPTION
        "The value of vRtrMldIfGroupAddressType indicates the type of 
         IP multicast group address for which this entry contains information."
    ::= { vRtrMldIfGroupEntry 1 }  

vRtrMldIfGroupAddress OBJECT-TYPE
    SYNTAX     InetAddress (SIZE(16))
    MAX-ACCESS not-accessible
    STATUS     current
    DESCRIPTION
        "The value of vRtrMldIfGroupAddress indicates the IP multicast group 
         address for which this entry contains information."
    ::= { vRtrMldIfGroupEntry 2 }

vRtrMldIfGroupType OBJECT-TYPE
    SYNTAX     INTEGER {
                   static(1),
                   dynamic(2)
               }
    MAX-ACCESS read-only
    STATUS     current
    DESCRIPTION
        "The value of vRtrMldIfGroupType indicates how this group entry 
         was learned. If this group entry was learned by the MLD, it will be set to
         'dynamic'. For statically configured groups, the value will be 
         set to 'static'."
    ::= { vRtrMldIfGroupEntry 3 }

vRtrMldIfGroupUpTime OBJECT-TYPE
    SYNTAX     TimeInterval
    MAX-ACCESS read-only
    STATUS     current
    DESCRIPTION
        "The value of vRtrMldIfGroupUpTime indicates the time elapsed since 
         this entry was created."
    ::= { vRtrMldIfGroupEntry 4 }

vRtrMldIfGroupExpiryTime OBJECT-TYPE
    SYNTAX     TimeInterval
    MAX-ACCESS read-only
    STATUS     current
    DESCRIPTION
        "The value of vRtrMldIfGroupExpiryTime indicates the minimum amount 
         of time remaining before this entry will be aged out.

         If the value of vRtrMldIfGroupType is 'static', the value of 
         vRtrMldIfGroupExpiryTime will be set to maximum, which is 2147483647." 
    ::= { vRtrMldIfGroupEntry 5 }

vRtrMldIfGroupVer1HostTimer OBJECT-TYPE
    SYNTAX     TimeInterval
    MAX-ACCESS read-only
    STATUS     current
    DESCRIPTION
        "The value of vRtrMldIfGroupVer1HostTimer indicates the time remaining 
         until the local router will assume that there are no longer any 
         MLD version 1 members on the IP subnet attached to this interface.  
         Upon hearing any MLDv1 Membership Report, this value is reset to 
         the group membership timer.  While this time remaining is non-zero,
         the local router ignores any MLD Leave messages for this
         group that it receives on this interface."
    ::= { vRtrMldIfGroupEntry 6 }

vRtrMldIfGroupMode OBJECT-TYPE
    SYNTAX     INTEGER {
                   include (1),
                   exclude (2)
               }
    MAX-ACCESS read-only
    STATUS     current
    DESCRIPTION
        "The value of vRtrMldIfGroupMode is based on the type of 
         membership report(s) received on the interface for the group. 
         In the 'include' mode, reception of packets sent to the 
         specified multicast address is requested only from those 
         IP source addresses listed in the source-list parameter of 
         the MLD membership report. 

         In 'exclude' mode, reception of packets sent to the given
         multicast address is requested from all IP source addresses 
         except those listed in the source-list parameter.

         vRtrMldIfGrpSrcTable lists the sources corresponding to this group,
         if any."
    ::= { vRtrMldIfGroupEntry 7 }

vRtrMldIfGroupCompatMode OBJECT-TYPE
    SYNTAX     TmnxMldVersion
    MAX-ACCESS read-only
    STATUS     current
    DESCRIPTION
        "The value of vRtrMldIfGroupCompatMode is used in order for routers 
         to be compatible with older version routers. MLDv2 hosts MUST operate 
         in version 1 and version 2 compatibility modes.  MLDv2 hosts MUST 
         keep state per local interface regarding the compatibility mode of 
         each attached network.  A host's compatibility mode is determined 
         from the Host Compatibility Mode variable which can be in
         one of two states:  MLDv1 or MLDv2.  This variable is
         kept per interface and is dependent on the version of General Queries
         heard on that interface as well as the Older Version Querier Present
         timers for the interface."
    ::= { vRtrMldIfGroupEntry 8 }

vRtrMldIfGroupLstRprtrType   OBJECT-TYPE
    SYNTAX     InetAddressType
    MAX-ACCESS read-only
    STATUS     current
    DESCRIPTION
        "The value of vRtrMldIfGroupLstRprtrType indicates 
         the Address type of vRtrMldIfGroupLastReporter."
    ::= { vRtrMldIfGroupEntry 9 }

vRtrMldIfGroupLastReporter    OBJECT-TYPE
    SYNTAX     InetAddress (SIZE(0|16))
    MAX-ACCESS read-only
    STATUS     current
    DESCRIPTION
        "The value of vRtrMldIfGroupLastReporter indicates 
         the IP address of the source of the last membership report
         received for this IP Multicast group address on this
         interface."
    ::= { vRtrMldIfGroupEntry 10 }


--
--  The MLD Interface Source Group Table
--

vRtrMldIfGrpSrcTable OBJECT-TYPE
    SYNTAX     SEQUENCE OF VRtrMldIfGrpSrcEntry
    MAX-ACCESS not-accessible
    STATUS     current
    DESCRIPTION
        "The vRtrMldIfGrpSrcTable contains objects for 
         the IP multicast sources corresponding to the 
         IP multicast groups for which there are members 
         on a particular interface. This table represents
         the MLD source, group database."
    ::= { vRtrMldIfObjs 4 }

vRtrMldIfGrpSrcEntry OBJECT-TYPE
    SYNTAX     VRtrMldIfGrpSrcEntry
    MAX-ACCESS not-accessible
    STATUS     current
    DESCRIPTION
        "An entry in the vRtrMldIfGrpSrcTable. 
         Each entry represents a source address from which receivers are
         interested or not interested in receiving multicast traffic from."
    INDEX      { vRtrID, 
                 vRtrIfIndex, 
                 vRtrMldIfGroupAddressType,
                 vRtrMldIfGroupAddress,
                 vRtrMldIfGrpSrcAddrType,  
                 vRtrMldIfGrpSrcAddress }
    ::= { vRtrMldIfGrpSrcTable 1 }

VRtrMldIfGrpSrcEntry ::= SEQUENCE {
    vRtrMldIfGrpSrcAddrType         InetAddressType,
    vRtrMldIfGrpSrcAddress          InetAddress,
    vRtrMldIfGrpSrcExpiryTime       TimeInterval,
    vRtrMldIfGrpSrcType             INTEGER
}

vRtrMldIfGrpSrcAddrType OBJECT-TYPE
    SYNTAX     InetAddressType
    MAX-ACCESS not-accessible
    STATUS     current
    DESCRIPTION
        "The value of vRtrMldIfGrpSrcAddrType indicates the address type of 
         vRtrMldIfGrpSrcAddress."
    ::= { vRtrMldIfGrpSrcEntry 1 }

vRtrMldIfGrpSrcAddress OBJECT-TYPE
    SYNTAX     InetAddress (SIZE(16))
    MAX-ACCESS not-accessible
    STATUS     current
    DESCRIPTION
        "The value of vRtrMldIfGrpSrcAddress indicates the address of the 
         source sending multicast traffic to the group identified by 
         vRtrMldIfGroupAddress.
         
         If the value of vRtrMldIfGroupMode corresponding to this entry is 
         'include', the receivers are interested in receiving traffic 
         from this source.
         
         If the value of vRtrMldIfGroupMode corresponding to this entry is 
         'exclude' and if the value of vRtrMldIfGrpSrcExpiryTime is '0',
         the receivers are not interested in receiving traffic from this 
         source."
    ::= { vRtrMldIfGrpSrcEntry 2 }

vRtrMldIfGrpSrcExpiryTime OBJECT-TYPE
    SYNTAX     TimeInterval
    MAX-ACCESS read-only
    STATUS     current
    DESCRIPTION
        "The value of vRtrMldIfGrpSrcExpiryTime indicates the minimum amount 
         of time remaining before this entry will be aged out.
         
         If the value of vRtrMldIfGrpSrcExpiryTime is non-zero and the 
         value of vRtrMldIfGroupMode corresponding to this entry is 'include',
         it means that there are currently one or more systems which desire 
         to receive multicast traffic for this source. If this timer expires 
         and the value of vRtrMldIfGroupMode is 'include', the router 
         concludes that traffic from this particular source is no longer 
         desired on the attached network, and deletes this entry.
         This timer is treated differently when the value of vRtrMldIfGroupMode
         is 'exclude'. If the value of vRtrMldIfGrpSrcExpiryTime is non-zero 
         and router filter-mode for the group is 'exclude', it means that at 
         least one system desires to receive multicast traffic from this source.
         It should therefore be forwarded by a router on the network."
    ::= { vRtrMldIfGrpSrcEntry 3 }

vRtrMldIfGrpSrcType OBJECT-TYPE
    SYNTAX     INTEGER {
                   static(1),
                   dynamic(2)
               }
    MAX-ACCESS read-only
    STATUS     current
    DESCRIPTION
        "The value of vRtrMldIfGrpSrcType indicates how this source entry 
         was learned. If this source entry was learned by the MLD, it will be 
         set to 'dynamic'. For statically configured sources, the value 
         will be set to 'static'."
    ::= { vRtrMldIfGrpSrcEntry 4 }


--
--  The MLD Interface Static Source Group Table
--

vRtrMldIfStatcGrpSrcTblLstChngd OBJECT-TYPE
    SYNTAX       TimeStamp
    MAX-ACCESS   read-only
    STATUS       current
    DESCRIPTION
        "The value of vRtrMldIfStatcGrpSrcTblLstChngd indicates 
         the sysUpTime at the time of the last modification of 
         an entry in the vRtrMldIfStaticGrpSrcTable.

         If no changes were made to the table since the last re-initialization
         of the local network management subsystem, then this object
         contains a zero value."
    ::= { vRtrMldIfObjs 5 }

vRtrMldIfStaticGrpSrcTable OBJECT-TYPE
    SYNTAX     SEQUENCE OF VRtrMldIfStaticGrpSrcEntry
    MAX-ACCESS not-accessible
    STATUS     current
    DESCRIPTION
        "The vRtrMldIfStaticGrpSrcTable contains objects for 
         the IP multicast sources corresponding to the 
         IP multicast groups which are statically configured."
    ::= { vRtrMldIfObjs 6 }

vRtrMldIfStaticGrpSrcEntry OBJECT-TYPE
    SYNTAX     VRtrMldIfStaticGrpSrcEntry
    MAX-ACCESS not-accessible
    STATUS     current
    DESCRIPTION
        "An entry in the vRtrMldIfStaticGrpSrcTable. Entries can         
         be created or deleted by an SNMP SET request to
         vRtrMldIfStaticGrpSrcRowStatus."
    INDEX      { vRtrID, 
                 vRtrIfIndex, 
                 vRtrMldIfGroupAddressType,
                 vRtrMldIfGroupAddress,
                 vRtrMldIfGrpSrcAddrType, 
                 vRtrMldIfGrpSrcAddress }
    ::= { vRtrMldIfStaticGrpSrcTable 1 }

VRtrMldIfStaticGrpSrcEntry ::= SEQUENCE {
    vRtrMldIfStaticGrpSrcRowStatus       RowStatus,
    vRtrMldIfStaticGrpSrcLstChanged      TimeStamp
}

vRtrMldIfStaticGrpSrcRowStatus OBJECT-TYPE
    SYNTAX     RowStatus
    MAX-ACCESS read-create
    STATUS     current
    DESCRIPTION
        "The value of vRtrMldIfStaticGrpSrcRowStatus specifies 
         the row status used for creation or deletion of
         vRtrMldIfStaticGrpSrcTable entries."
    ::= { vRtrMldIfStaticGrpSrcEntry 1 }

vRtrMldIfStaticGrpSrcLstChanged       OBJECT-TYPE
    SYNTAX      TimeStamp
    MAX-ACCESS  read-only
    STATUS      current
    DESCRIPTION
        "The value of vRtrMldIfStaticGrpSrcLstChanged indicates 
         the sysUpTime when this row was last modified."
    ::= { vRtrMldIfStaticGrpSrcEntry 2 }

--
--  The MLD Interface Statistics Table
--

vRtrMldIfStatsTable OBJECT-TYPE
    SYNTAX     SEQUENCE OF VRtrMldIfStatsEntry
    MAX-ACCESS not-accessible
    STATUS     current
    DESCRIPTION
        "The vRtrMldIfStatsTable contains objects corresponding
         to the MLD statistics for a particular interface."
    ::= { vRtrMldIfObjs 7 }

vRtrMldIfStatsEntry OBJECT-TYPE
    SYNTAX     VRtrMldIfStatsEntry
    MAX-ACCESS not-accessible
    STATUS     current
    DESCRIPTION
        "An entry in the vRtrMldIfStatsTable."
    AUGMENTS      { vRtrMldIfEntry }
    ::= { vRtrMldIfStatsTable 1 }

VRtrMldIfStatsEntry ::= SEQUENCE {
    vRtrMldIfTxGenQueries         Counter32,
    vRtrMldIfTxGrpQueries         Counter32,
    vRtrMldIfTxGrpSrcQueries      Counter32,
    vRtrMldIfTxV1Reports          Counter32,
    vRtrMldIfTxV2Reports          Counter32,
    vRtrMldIfTxLeaves             Counter32,
    vRtrMldIfTxErrors             Counter32,
    vRtrMldIfRxGenQueries         Counter32,
    vRtrMldIfRxGrpQueries         Counter32,
    vRtrMldIfRxGrpSrcQueries      Counter32,
    vRtrMldIfRxV1Reports          Counter32,
    vRtrMldIfRxV2Reports          Counter32,
    vRtrMldIfRxLeaves             Counter32,
    vRtrMldIfRxBadLenPkts         Counter32,
    vRtrMldIfRxBadChecksumPkts    Counter32,
    vRtrMldIfRxUnknownTypePkts    Counter32,
    vRtrMldIfRxBadReceiveIfPkts   Counter32,
    vRtrMldIfRxNonLocal           Counter32,
    vRtrMldIfRxWrongVersions      Counter32,
    vRtrMldIfImportPolicyDrops    Counter32,
    vRtrMldIfRxNoRtrAlertPkts     Counter32,
    vRtrMldIfRxBadEncodings       Counter32,
    vRtrMldIfRxPktDrops           Counter32,
    vRtrMldIfStatsStarGTypes      Gauge32,
    vRtrMldIfStatsSGTypes         Gauge32,
    vRtrMldIfRxLocalScopePkts     Counter32,
    vRtrMldIfRxRsvdScopePkts      Counter32,
    vRtrMldIfStatsMcacPolicyDrops Counter32
}

vRtrMldIfTxGenQueries OBJECT-TYPE
    SYNTAX       Counter32
    MAX-ACCESS   read-only
    STATUS       current
    DESCRIPTION
        "The value of vRtrMldIfTxGenQueries indicates the number of MLD 
         General Queries transmitted on this interface."
    ::= { vRtrMldIfStatsEntry 1 }

vRtrMldIfTxGrpQueries OBJECT-TYPE
    SYNTAX       Counter32
    MAX-ACCESS   read-only
    STATUS       current
    DESCRIPTION
        "The value of vRtrMldIfTxGrpQueries indicates the number of MLD 
         Group Specific Queries transmitted on this interface."
    ::= { vRtrMldIfStatsEntry 2 }

vRtrMldIfTxGrpSrcQueries OBJECT-TYPE
    SYNTAX       Counter32
    MAX-ACCESS   read-only
    STATUS       current
    DESCRIPTION
        "The value of vRtrMldIfTxGrpSrcQueries indicates the number of MLD 
         Group and Source Specific Queries transmitted on this interface."
    ::= { vRtrMldIfStatsEntry 3 }

vRtrMldIfTxV1Reports OBJECT-TYPE
    SYNTAX       Counter32
    MAX-ACCESS   read-only
    STATUS       current
    DESCRIPTION
        "The value of vRtrMldIfTxV1Reports indicates the total number of 
         MLD V1 Reports transmitted on this interface."
    ::= { vRtrMldIfStatsEntry 4 }

vRtrMldIfTxV2Reports OBJECT-TYPE
    SYNTAX       Counter32
    MAX-ACCESS   read-only
    STATUS       current
    DESCRIPTION
        "The value of vRtrMldIfTxV2Reports indicates the total number of 
         MLD V2 Reports transmitted on this interface."
    ::= { vRtrMldIfStatsEntry 5 }

vRtrMldIfTxLeaves OBJECT-TYPE
    SYNTAX       Counter32
    MAX-ACCESS   read-only
    STATUS       current
    DESCRIPTION
        "The value of vRtrMldIfTxLeaves indicates the total number of MLD
         Leaves transmitted on this interface."
    ::= { vRtrMldIfStatsEntry 6 }

vRtrMldIfTxErrors OBJECT-TYPE
    SYNTAX       Counter32
    MAX-ACCESS   read-only
    STATUS       current
    DESCRIPTION
        "The value of vRtrMldIfTxErrors indicates the total number of times
         there was an error transmitting the MLD packets on this interface."
    ::= { vRtrMldIfStatsEntry 7 }

vRtrMldIfRxGenQueries OBJECT-TYPE
    SYNTAX       Counter32
    MAX-ACCESS   read-only
    STATUS       current
    DESCRIPTION
        "The value of vRtrMldIfRxGenQueries indicates the total number of MLD 
         General Queries received on this interface."
    ::= { vRtrMldIfStatsEntry 8 }

vRtrMldIfRxGrpQueries OBJECT-TYPE
    SYNTAX       Counter32
    MAX-ACCESS   read-only
    STATUS       current
    DESCRIPTION
        "The value of vRtrMldIfRxGrpQueries indicates the number of MLD 
         Group Specific Queries received on this interface."
    ::= { vRtrMldIfStatsEntry 9 }

vRtrMldIfRxGrpSrcQueries OBJECT-TYPE
    SYNTAX       Counter32
    MAX-ACCESS   read-only
    STATUS       current
    DESCRIPTION
        "The value of vRtrMldIfRxGrpSrcQueries indicates the number of MLD 
         Group and Source Specific Queries received on this interface."
    ::= { vRtrMldIfStatsEntry 10 }

vRtrMldIfRxV1Reports OBJECT-TYPE
    SYNTAX       Counter32
    MAX-ACCESS   read-only
    STATUS       current
    DESCRIPTION
        "The value of vRtrMldIfRxV1Reports indicates the total number of 
         MLD V1 Reports received on this interface."
    ::= { vRtrMldIfStatsEntry 11 }

vRtrMldIfRxV2Reports OBJECT-TYPE
    SYNTAX       Counter32
    MAX-ACCESS   read-only
    STATUS       current
    DESCRIPTION
        "The value of vRtrMldIfRxV2Reports indicates the total number of 
         MLD V2 Reports received on this interface."
    ::= { vRtrMldIfStatsEntry 12 }

vRtrMldIfRxLeaves OBJECT-TYPE
    SYNTAX       Counter32
    MAX-ACCESS   read-only
    STATUS       current
    DESCRIPTION
        "The value of vRtrMldIfRxLeaves indicates the total number of 
         MLD V2 Leaves received on this interface."
    ::= { vRtrMldIfStatsEntry 13 }

vRtrMldIfRxBadLenPkts OBJECT-TYPE
    SYNTAX       Counter32
    MAX-ACCESS   read-only
    STATUS       current
    DESCRIPTION
        "The value of vRtrMldIfRxBadLenPkts indicates the total number of 
         MLD packets with bad length received on this interface."
    ::= { vRtrMldIfStatsEntry 14 }

vRtrMldIfRxBadChecksumPkts OBJECT-TYPE
    SYNTAX       Counter32
    MAX-ACCESS   read-only
    STATUS       current
    DESCRIPTION
        "The value of vRtrMldIfRxBadChecksumPkts indicates the total number of 
         MLD packets with bad checksum received on this interface."
    ::= { vRtrMldIfStatsEntry 15 }

vRtrMldIfRxUnknownTypePkts OBJECT-TYPE
    SYNTAX       Counter32
    MAX-ACCESS   read-only
    STATUS       current
    DESCRIPTION
        "The value of vRtrMldIfRxUnknownTypePkts indicates the total number of 
         MLD packets with unknown type received on this interface."
    ::= { vRtrMldIfStatsEntry 16 }

vRtrMldIfRxBadReceiveIfPkts OBJECT-TYPE
    SYNTAX       Counter32
    MAX-ACCESS   read-only
    STATUS       current
    DESCRIPTION
        "The value of vRtrMldIfRxBadReceiveIfPkts indicates the total 
         number of MLD packets incorrectly received on this interface."
    ::= { vRtrMldIfStatsEntry 17 }

vRtrMldIfRxNonLocal OBJECT-TYPE
    SYNTAX       Counter32
    MAX-ACCESS   read-only
    STATUS       current
    DESCRIPTION
        "The value of vRtrMldIfRxNonLocal indicates the total number of 
         MLD packets received from a non-local sender."
    ::= { vRtrMldIfStatsEntry 18 }

vRtrMldIfRxWrongVersions OBJECT-TYPE
    SYNTAX       Counter32
    MAX-ACCESS   read-only
    STATUS       current
    DESCRIPTION
        "The value of vRtrMldIfRxWrongVersions indicates the total number of 
         MLD packets with wrong versions received on this interface."
    ::= { vRtrMldIfStatsEntry 19 }

vRtrMldIfImportPolicyDrops OBJECT-TYPE
    SYNTAX       Counter32
    MAX-ACCESS   read-only
    STATUS       current
    DESCRIPTION
        "The value of vRtrMldIfImportPolicyDrops indicates the total number of 
         times the MLD protocol instance matched the host IP address or 
         group or source addresses specified in the import policy
         vRtrMldIfImportPolicy."
    ::= { vRtrMldIfStatsEntry 20 }

vRtrMldIfRxNoRtrAlertPkts OBJECT-TYPE
    SYNTAX       Counter32
    MAX-ACCESS   read-only
    STATUS       current
    DESCRIPTION
        "The value of vRtrMldIfRxNoRtrAlertPkts indicates the total number of 
         MLDv2 packets received on this interface which did not have the 
         router alert flag set."
    ::= { vRtrMldIfStatsEntry 21 }

vRtrMldIfRxBadEncodings OBJECT-TYPE
    SYNTAX       Counter32
    MAX-ACCESS   read-only
    STATUS       current
    DESCRIPTION
        "The value of vRtrMldIfRxBadEncodings indicates the total number of 
         MLD packets received on this interface which were not encoded
         correctly."
    ::= { vRtrMldIfStatsEntry 22 }

vRtrMldIfRxPktDrops OBJECT-TYPE
    SYNTAX       Counter32
    MAX-ACCESS   read-only
    STATUS       current
    DESCRIPTION
        "The value of vRtrMldIfRxPktDrops indicates the total number of 
         MLD packets that were received on this interface but were dropped."
    ::= { vRtrMldIfStatsEntry 23 }

vRtrMldIfStatsStarGTypes OBJECT-TYPE
    SYNTAX       Gauge32
    MAX-ACCESS   read-only
    STATUS       current
    DESCRIPTION
        "vRtrMldIfStatsStarGTypes indicates the number of entries on 
         this interface for which the source type is 'starG'."
    ::= { vRtrMldIfStatsEntry 24 }

vRtrMldIfStatsSGTypes OBJECT-TYPE
    SYNTAX       Gauge32
    MAX-ACCESS   read-only
    STATUS       current
    DESCRIPTION
        "The value of vRtrMldIfStatsSGTypes indicates the number of entries on 
         this interface for which the source type is 'sg'."
    ::= { vRtrMldIfStatsEntry 25 }

vRtrMldIfRxLocalScopePkts OBJECT-TYPE
    SYNTAX       Counter32
    MAX-ACCESS   read-only
    STATUS       current
    DESCRIPTION
        "The value of the object vRtrMldIfRxLocalScopePkts indicates 
         the number of MLD packets received on the link-local scope IPv6 
         multicast address."
    ::= { vRtrMldIfStatsEntry 26 }

vRtrMldIfRxRsvdScopePkts OBJECT-TYPE
    SYNTAX       Counter32
    MAX-ACCESS   read-only
    STATUS       current
    DESCRIPTION
        "The value of the object vRtrMldIfRxRsvdScopePkts indicates 
         the number of MLD packets received on the reserved scope
         IPv6 multicast address."
    ::= { vRtrMldIfStatsEntry 27 }

vRtrMldIfStatsMcacPolicyDrops OBJECT-TYPE
    SYNTAX       Counter32
    MAX-ACCESS   read-only
    STATUS       current
    DESCRIPTION
        "The value of the object vRtrMldIfStatsMcacPolicyDrops indicates 
         the number times an MLD Group is dropped because of applying a
         multicast CAC policy on this interface."
    ::= { vRtrMldIfStatsEntry 28 }

--
--  The MLD Interface Source Specific Multicast (SSM) Translate Table
--

vRtrMldIfSsmTltTableLastChanged OBJECT-TYPE
    SYNTAX       TimeStamp
    MAX-ACCESS   read-only
    STATUS       current
    DESCRIPTION
        "The value of vRtrMldIfSsmTltTableLastChanged indicates the
         sysUpTime value at the time of the last modification of an entry
         in the vRtrMldIfSsmTransTable.
        
         If no changes were made to the table since the last re-initialization
         of the local network management subsystem, then this object
         contains a zero value."
    ::= { vRtrMldIfObjs 8 }

vRtrMldIfSsmTransTable OBJECT-TYPE
    SYNTAX     SEQUENCE OF VRtrMldIfSsmTransEntry
    MAX-ACCESS not-accessible
    STATUS     current
    DESCRIPTION
        "The vRtrMldIfSsmTransTable is used to configure group ranges which
         are translated to SSM (S,G) entries for interface."
    ::= { vRtrMldIfObjs 9 }

vRtrMldIfSsmTransEntry OBJECT-TYPE
    SYNTAX     VRtrMldIfSsmTransEntry
    MAX-ACCESS not-accessible
    STATUS     current
    DESCRIPTION
        "An entry in the vRtrMldIfSsmTransTable. Entries can         
         be created or deleted by an SNMP SET request to 
         vRtrMldIfSsmTransRowStatus."
    INDEX      { vRtrID, 
                 vRtrIfIndex,
                 vRtrMldIfSsmTransGrpAddrType1,
                 vRtrMldIfSsmTransGrpAddr1,
                 vRtrMldIfSsmTransGrpAddrType2, 
                 vRtrMldIfSsmTransGrpAddr2,
                 vRtrMldIfSsmTransSrcAddrType, 
                 vRtrMldIfSsmTransSrcAddr }
    ::= { vRtrMldIfSsmTransTable 1 }

VRtrMldIfSsmTransEntry ::= SEQUENCE {
    vRtrMldIfSsmTransGrpAddrType1  InetAddressType, 
    vRtrMldIfSsmTransGrpAddr1      InetAddress,
    vRtrMldIfSsmTransGrpAddrType2  InetAddressType,    
    vRtrMldIfSsmTransGrpAddr2      InetAddress,
    vRtrMldIfSsmTransSrcAddrType   InetAddressType,
    vRtrMldIfSsmTransSrcAddr       InetAddress,
    vRtrMldIfSsmTransRowStatus     RowStatus
}

vRtrMldIfSsmTransGrpAddrType1 OBJECT-TYPE
    SYNTAX     InetAddressType
    MAX-ACCESS not-accessible
    STATUS     current
    DESCRIPTION
        "The value of vRtrMldIfSsmTransGrpAddrType1 indicates the starting 
         address type of the group range."
    ::= { vRtrMldIfSsmTransEntry 1 }

vRtrMldIfSsmTransGrpAddr1 OBJECT-TYPE
    SYNTAX     InetAddress (SIZE(16))
    MAX-ACCESS not-accessible
    STATUS     current
    DESCRIPTION
        "The value of vRtrMldIfSsmTransGrpAddr1 indicates the start of 
         the group range."
    ::= { vRtrMldIfSsmTransEntry 2 }

vRtrMldIfSsmTransGrpAddrType2 OBJECT-TYPE
    SYNTAX     InetAddressType
    MAX-ACCESS not-accessible
    STATUS     current
    DESCRIPTION
        "The value of vRtrMldIfSsmTransGrpAddrType2 indicates the ending 
         address type of the group range."
    ::= { vRtrMldIfSsmTransEntry 3 }

vRtrMldIfSsmTransGrpAddr2 OBJECT-TYPE
    SYNTAX     InetAddress (SIZE(16))
    MAX-ACCESS not-accessible
    STATUS     current
    DESCRIPTION
        "The value of vRtrMldIfSsmTransGrpAddr2 indicates the end 
         of the group range."
    ::= { vRtrMldIfSsmTransEntry 4 }

vRtrMldIfSsmTransSrcAddrType OBJECT-TYPE
    SYNTAX     InetAddressType
    MAX-ACCESS not-accessible
    STATUS     current 
    DESCRIPTION
        "The value of vRtrMldIfSsmTransSrcAddrType indicates the type of 
         the source address for this group range."
    ::= { vRtrMldIfSsmTransEntry 5 }

vRtrMldIfSsmTransSrcAddr OBJECT-TYPE
    SYNTAX     InetAddress (SIZE(16))
    MAX-ACCESS not-accessible
    STATUS     current
    DESCRIPTION
        "The value of vRtrMldIfSsmTransSrcAddr indicates
         the source address for this group range. Whenever a (*,G) report is
         received in the range specified by vRtrMldIfSsmTransGrpAddr1 and
         vRtrMldIfSsmTransGrpAddr2, it is translated to an (S,G) report
         with the value of this object as the source address."
    ::= { vRtrMldIfSsmTransEntry 6 }

vRtrMldIfSsmTransRowStatus OBJECT-TYPE
    SYNTAX     RowStatus
    MAX-ACCESS read-create
    STATUS     current
    DESCRIPTION
        "The value of vRtrMldIfSsmTransRowStatus is used to 
         create or delete an entry in this table."
    ::= { vRtrMldIfSsmTransEntry 7 }

--
--  The MLD Interface Multicast CAC Level table
--

vRtrMldIfMcacLevelTable  OBJECT-TYPE
    SYNTAX      SEQUENCE OF VRtrMldIfMcacLevelEntry
    MAX-ACCESS  not-accessible
    STATUS      current
    DESCRIPTION
        "The vRtrMldIfMcacLevelTable has an entry for each multicast 
         CAC policy constraint level configured on this system."
    ::= { vRtrMldIfObjs 10 }

vRtrMldIfMcacLevelEntry    OBJECT-TYPE
    SYNTAX      VRtrMldIfMcacLevelEntry
    MAX-ACCESS  not-accessible
    STATUS      current
    DESCRIPTION
        "Each row entry represents a particular multicast CAC 
         policy level constraints. Entries are created/deleted
         by the user."
    INDEX      { vRtrID, 
                 vRtrIfIndex, 
                 tmnxMcacLevelId  }
    ::= { vRtrMldIfMcacLevelTable 1}

VRtrMldIfMcacLevelEntry ::= SEQUENCE
   {
       vRtrMldIfMcacLevelRowStatus   RowStatus,
       vRtrMldIfMcacLevelBW          Unsigned32
   }

vRtrMldIfMcacLevelRowStatus  OBJECT-TYPE
    SYNTAX      RowStatus
    MAX-ACCESS  read-create
    STATUS      current
    DESCRIPTION
        "The value of vRtrMldIfMcacLevelRowStatus is used for  
         creation/deletion of level constraint in a CAC policy."
    ::= { vRtrMldIfMcacLevelEntry 1 }

vRtrMldIfMcacLevelBW            OBJECT-TYPE
    SYNTAX      Unsigned32 (0..2147483647)
    UNITS       "kbps"
    MAX-ACCESS  read-create
    STATUS      current
    DESCRIPTION
        "The value of vRtrMldIfMcacLevelBW specifies the bandwidth in
         kilo-bits per second(kbps) for the level."
    DEFVAL { 1 }        
    ::= { vRtrMldIfMcacLevelEntry 2 }

--
--  The MLD Interface Multicast CAC Lag table
--

vRtrMldIfMcacLagTable    OBJECT-TYPE
    SYNTAX      SEQUENCE OF VRtrMldIfMcacLagEntry
    MAX-ACCESS  not-accessible
    STATUS      current
    DESCRIPTION
        "The vRtrMldIfMcacLagTable has an entry for each lag
         port configured for a multicast CAC policy 
         bundle on this system."
    ::= { vRtrMldIfObjs 11 }

vRtrMldIfMcacLagEntry OBJECT-TYPE
    SYNTAX      VRtrMldIfMcacLagEntry
    MAX-ACCESS  not-accessible
    STATUS      current
    DESCRIPTION
        "Each row entry represents a particular multicast CAC 
         lag port constraints. Entries are created/deleted by the user."
    INDEX { vRtrID, 
            vRtrIfIndex, 
            tmnxMcacLagPortsDown }
    ::= { vRtrMldIfMcacLagTable 1}

VRtrMldIfMcacLagEntry ::= SEQUENCE
   {
       vRtrMldIfMcacLagRowStatus   RowStatus,
       vRtrMldIfMcacLagLevel       Unsigned32
   }


vRtrMldIfMcacLagRowStatus   OBJECT-TYPE
    SYNTAX      RowStatus
    MAX-ACCESS  read-create
    STATUS      current
    DESCRIPTION
        "The value of vRtrMldIfMcacLagRowStatus is used for creation/deletion
         of lag constraint in a CAC policy."
    ::= { vRtrMldIfMcacLagEntry 1 }

vRtrMldIfMcacLagLevel  OBJECT-TYPE
    SYNTAX      Unsigned32 (1..8)
    MAX-ACCESS  read-create
    STATUS      current
    DESCRIPTION
        "The value of vRtrMldIfMcacLagLevel specifies the level id to use 
         when the value of tmnxMcacLagPortsDown matches the actual number
         of ports down in a lag.

         Using the value of vRtrMldIfMcacLagLevel as an index, the  
         operational interface unconstrained bandwidth will be set to 
         vRtrMldIfMcacLevelBW.
    
         By default for all lag constraints the interface level will be
         set to 1 at row creation."
    DEFVAL { 1 }         
    ::= { vRtrMldIfMcacLagEntry 2 }

--
--  The MLD Interface Static Source Group Range Table
--
vRtrMldIfSGrpRangeSrcTblLstChgd OBJECT-TYPE
    SYNTAX       TimeStamp
    MAX-ACCESS   read-only
    STATUS       current
    DESCRIPTION
        "The value of vRtrMldIfSGrpRangeSrcTblLstChgd indicates the sysUpTime
         at the time of the last modification of an entry in the
         vRtrMldIfSGrpRangeSrcTable.

         If no changes were made to the table since the last re-initialization
         of the local network management subsystem, then this object
         contains a zero value."
    ::= { vRtrMldIfObjs 12 }

vRtrMldIfSGrpRangeSrcTable OBJECT-TYPE
    SYNTAX     SEQUENCE OF VRtrMldIfSGrpRangeSrcEntry
    MAX-ACCESS not-accessible
    STATUS     current
    DESCRIPTION
        "The vRtrMldIfSGrpRangeSrcTable contains the IP multicast sources
         corresponding to the IP multicast group ranges which are statically
         configured."
    ::= { vRtrMldIfObjs 13 }

vRtrMldIfSGrpRangeSrcEntry OBJECT-TYPE
    SYNTAX     VRtrMldIfSGrpRangeSrcEntry
    MAX-ACCESS not-accessible
    STATUS     current
    DESCRIPTION
        "An entry in the vRtrMldIfSGrpRangeSrcTable. Entries can be created
         or deleted by an SNMP SET request to vRtrMldIfSGrpRangeSrcRowStatus."
    INDEX      { vRtrID, 
                 vRtrIfIndex,
                 vRtrMldIfSGrpRangeStartAddrType,
                 vRtrMldIfSGrpRangeStartAddr,
                 vRtrMldIfSGrpRangeEndAddrType,
                 vRtrMldIfSGrpRangeEndAddr,
                 vRtrMldIfSGrpRangeStepAddrType,
                 vRtrMldIfSGrpRangeStepAddr,
                 vRtrMldIfSGrpRangeSrcAddrType,
                 vRtrMldIfSGrpRangeSrcAddr }
    ::= { vRtrMldIfSGrpRangeSrcTable 1 }

VRtrMldIfSGrpRangeSrcEntry ::= SEQUENCE {
    vRtrMldIfSGrpRangeStartAddrType  InetAddressType, 
    vRtrMldIfSGrpRangeStartAddr      InetAddress,
    vRtrMldIfSGrpRangeEndAddrType    InetAddressType, 
    vRtrMldIfSGrpRangeEndAddr        InetAddress,
    vRtrMldIfSGrpRangeStepAddrType   InetAddressType, 
    vRtrMldIfSGrpRangeStepAddr       InetAddress,
    vRtrMldIfSGrpRangeSrcAddrType    InetAddressType, 
    vRtrMldIfSGrpRangeSrcAddr        InetAddress,
    
    vRtrMldIfSGrpRangeSrcRowStatus   RowStatus,
    vRtrMldIfSGrpRangeLastChanged    TimeStamp,
    vRtrMldIfSGrpRangeGrpCount       Unsigned32
}

vRtrMldIfSGrpRangeStartAddrType OBJECT-TYPE
    SYNTAX     InetAddressType
    MAX-ACCESS not-accessible
    STATUS     current
    DESCRIPTION
        "The value of vRtrMldIfSGrpRangeStartAddrType indicates the address
         type of vRtrMldIfSGrpRangeStartAddr."
    ::= { vRtrMldIfSGrpRangeSrcEntry 1 }  

vRtrMldIfSGrpRangeStartAddr OBJECT-TYPE
    SYNTAX     InetAddress (SIZE(16))
    MAX-ACCESS not-accessible
    STATUS     current
    DESCRIPTION
        "The value of vRtrMldIfSGrpRangeStartAddr indicates the IP multicast 
         group-range start-address for which this entry contains information."
    ::= { vRtrMldIfSGrpRangeSrcEntry 2 }

vRtrMldIfSGrpRangeEndAddrType OBJECT-TYPE
    SYNTAX     InetAddressType
    MAX-ACCESS not-accessible
    STATUS     current
    DESCRIPTION
        "The value of vRtrMldIfSGrpRangeEndAddrType indicates the address
         type of vRtrMldIfSGrpRangeEndAddr."
    ::= { vRtrMldIfSGrpRangeSrcEntry 3 }  

vRtrMldIfSGrpRangeEndAddr OBJECT-TYPE
    SYNTAX     InetAddress (SIZE(16))
    MAX-ACCESS not-accessible
    STATUS     current
    DESCRIPTION
        "The value of vRtrMldIfSGrpRangeEndAddr indicates the IP multicast 
         group-range end-address for which this entry contains information.

         The value of vRtrMldIfSGrpRangeEndAddr should always be greater
         than the value of vRtrMldIfSGrpRangeStartAddr."
    ::= { vRtrMldIfSGrpRangeSrcEntry 4 }

vRtrMldIfSGrpRangeStepAddrType OBJECT-TYPE
    SYNTAX     InetAddressType
    MAX-ACCESS not-accessible
    STATUS     current
    DESCRIPTION
        "The value of vRtrMldIfSGrpRangeStepAddrType indicates the address
         type of vRtrMldIfSGrpRangeStepAddr."
    ::= { vRtrMldIfSGrpRangeSrcEntry 5 }  

vRtrMldIfSGrpRangeStepAddr OBJECT-TYPE
    SYNTAX     InetAddress (SIZE(16))
    MAX-ACCESS not-accessible
    STATUS     current
    DESCRIPTION
        "The value of vRtrMldIfSGrpRangeStepAddr indicates the step
         interval size within the group-range address."
    ::= { vRtrMldIfSGrpRangeSrcEntry 6 }

vRtrMldIfSGrpRangeSrcAddrType OBJECT-TYPE
    SYNTAX     InetAddressType
    MAX-ACCESS not-accessible
    STATUS     current
    DESCRIPTION
        "The value of vRtrMldIfSGrpRangeSrcAddrType indicates the address
         type of vRtrMldIfSGrpRangeSrcAddr."
    ::= { vRtrMldIfSGrpRangeSrcEntry 7 }

vRtrMldIfSGrpRangeSrcAddr OBJECT-TYPE
    SYNTAX     InetAddress (SIZE(16))
    MAX-ACCESS not-accessible
    STATUS     current
    DESCRIPTION
        "The value of vRtrMldIfSGrpRangeSrcAddr indicates the address of the 
         source that is joined for every IP multicast group in the range 
         vRtrMldIfSGrpRangeStartAddr-vRtrMldIfSGrpRangeEndAddr.
         
         A zero address value corresponds to a (*,G) join for every group
         in the range."
    ::= { vRtrMldIfSGrpRangeSrcEntry 8 }

vRtrMldIfSGrpRangeSrcRowStatus OBJECT-TYPE
    SYNTAX     RowStatus
    MAX-ACCESS read-create
    STATUS     current
    DESCRIPTION
        "The row status used for creation or deletion of 
         vRtrMldIfSGrpRangeSrcTable entries."
    ::= { vRtrMldIfSGrpRangeSrcEntry 9 }

vRtrMldIfSGrpRangeLastChanged OBJECT-TYPE
    SYNTAX      TimeStamp
    MAX-ACCESS  read-only
    STATUS      current
    DESCRIPTION
        "The sysUpTime when this row was last modified."
    ::= { vRtrMldIfSGrpRangeSrcEntry 10 }

vRtrMldIfSGrpRangeGrpCount OBJECT-TYPE
    SYNTAX     Unsigned32
    MAX-ACCESS read-only
    STATUS     current
    DESCRIPTION
        "The value of vRtrMldIfSGrpRangeGrpCount indicates the number of
         groups in the group-range."
    ::= { vRtrMldIfSGrpRangeSrcEntry 11 }

--
--  The MLD Host Table
--

vRtrMldHostTable OBJECT-TYPE
    SYNTAX     SEQUENCE OF VRtrMldHostEntry
    MAX-ACCESS not-accessible
    STATUS     current
    DESCRIPTION
        "The table listing the hosts for which MLD protocol
         operation is enabled."
    ::= { vRtrMldHostObjs 1 }

vRtrMldHostEntry OBJECT-TYPE
    SYNTAX     VRtrMldHostEntry
    MAX-ACCESS not-accessible
    STATUS     current
    DESCRIPTION
        "Each row entry in the vRtrMldHostTable represents a host on
         this router that participates in the Mld protocol."
    INDEX      { vRtrID, 
                 vRtrMldHostAddressType,
                 vRtrMldHostAddress,
                 vRtrMldHostMacAddress,
                 vRtrMldHostPppoeSessionId }
    ::= { vRtrMldHostTable 1 }

VRtrMldHostEntry ::= SEQUENCE {
    vRtrMldHostAddressType           InetAddressType,
    vRtrMldHostAddress               InetAddress,
    vRtrMldHostMacAddress            MacAddress,
    vRtrMldHostPppoeSessionId        TmnxPppoeSessionId,
    vRtrMldHostLastChangeTime        TimeStamp,
    vRtrMldHostOperState             MldGrpItfOperState,
    vRtrMldHostOperVersion           TmnxMldVersion,
    vRtrMldHostGroupCount            Unsigned32,
    vRtrMldHostNextGenQueryTime      Unsigned32,
    vRtrMldHostMaxGroupsTillNow      Counter32,
    vRtrMldHostFwdSvcId              TmnxServId,
    vRtrMldHostGrpIfId               InterfaceIndex,
    vRtrMldHostSubscriberId          TmnxSubIdentStringOrEmpty,
    vRtrMldHostMldPolicy             TPolicyStatementNameOrEmpty,
    vRtrMldHostMaxGroups             Unsigned32,
    vRtrMldHostAdminVersion          TmnxMldVersion,
    vRtrMldHostMaxSources            Unsigned32,
    vRtrMldHostMaxGrpSources         Unsigned32,
    vRtrMldHostQueryInterval              Unsigned32,
    vRtrMldHostLastLstnrQueryIntvl        Unsigned32,
    vRtrMldHostQueryResponseIntvl         Unsigned32,
    vRtrMldHostDisRtrAlertChk             TruthValue
}

vRtrMldHostAddressType OBJECT-TYPE
    SYNTAX     InetAddressType
    MAX-ACCESS not-accessible
    STATUS     current
    DESCRIPTION
        "The value of vRtrMldHostAddressType indicates the type of 
         address to be used for vRtrMldHostAddress."         
    ::= { vRtrMldHostEntry 1 }

vRtrMldHostAddress OBJECT-TYPE
    SYNTAX     InetAddress (SIZE(16))
    MAX-ACCESS not-accessible
    STATUS     current
    DESCRIPTION
        "The IP host address for which this entry
         contains information."
    ::= { vRtrMldHostEntry 2 }

vRtrMldHostMacAddress OBJECT-TYPE
    SYNTAX      MacAddress
    MAX-ACCESS  not-accessible
    STATUS      current
    DESCRIPTION
        "The value of vRtrMldHostMacAddress specifies the MAC address of
         this subscriber host."
    ::= { vRtrMldHostEntry 3 }

vRtrMldHostPppoeSessionId OBJECT-TYPE
    SYNTAX      TmnxPppoeSessionId
    MAX-ACCESS  not-accessible
    STATUS      current
    DESCRIPTION
        "The value of vRtrMldHostPppoeSessionId specifies the PPPoE
         session id of this subscriber host."
    ::= { vRtrMldHostEntry 4 }

vRtrMldHostLastChangeTime       OBJECT-TYPE
    SYNTAX      TimeStamp
    MAX-ACCESS  read-only
    STATUS      current
    DESCRIPTION
        "The sysUpTime when this row was last modified."
    ::= { vRtrMldHostEntry 5 }

vRtrMldHostOperState        OBJECT-TYPE
    SYNTAX      MldGrpItfOperState
    MAX-ACCESS  read-only
    STATUS      current
    DESCRIPTION
        "The current operational state of MLD protocol for this host."
    ::= { vRtrMldHostEntry 6 }

vRtrMldHostOperVersion OBJECT-TYPE
    SYNTAX     TmnxMldVersion
    MAX-ACCESS read-only
    STATUS     current
    DESCRIPTION
        "The operational version of MLD which is running for this host.
         If the value of vRtrMldIfAdminVersion is configured as '3' but 
         all of the routers in the local subnet of this interface use MLD 
         version v1 or v2, the operational version will be v1 or v2."
    ::= { vRtrMldHostEntry 7 }

vRtrMldHostGroupCount OBJECT-TYPE
    SYNTAX     Unsigned32
    MAX-ACCESS read-only
    STATUS     current
    DESCRIPTION
        "vRtrMldHostGroupCount is the number of multicast groups which have been
         learned by the router for this host."
    ::= { vRtrMldHostEntry 8 }

vRtrMldHostNextGenQueryTime OBJECT-TYPE
    SYNTAX     Unsigned32
    UNITS      "seconds"
    MAX-ACCESS read-only
    STATUS     current
    DESCRIPTION
            "If this router is the querier (vRtrMldIfQuerier is a 
             local address), vRtrMldHostNextGenQueryTime is the 
             time remaining before the general query is sent for this host.
             If this router is not the querier for the host, the value
             of this object will be zero."
    ::= { vRtrMldHostEntry 9 }

vRtrMldHostMaxGroupsTillNow OBJECT-TYPE
    SYNTAX     Counter32
    MAX-ACCESS read-only
    STATUS     current
    DESCRIPTION
        "The value of vRtrMldHostMaxGroupsTillNow indicates the highest value 
         that vRtrMldHostMaxGroups had till now."
    ::= { vRtrMldHostEntry 10 }

vRtrMldHostFwdSvcId OBJECT-TYPE
    SYNTAX       TmnxServId
    MAX-ACCESS   read-only
    STATUS       current
    DESCRIPTION  "The value of vRtrMldHostFwdSvcId specifies the forwarding 
                  service ID for a subscriber interface in a retailer 
                  context."
    DEFVAL       { 0 }
    ::= { vRtrMldHostEntry 11 }

vRtrMldHostGrpIfId OBJECT-TYPE
    SYNTAX       InterfaceIndex
    MAX-ACCESS   read-only
    STATUS       current
    DESCRIPTION  "The value of vRtrMldHostGrpIfId specifies the forwarding 
                  group interface."
    ::= { vRtrMldHostEntry 12 }

vRtrMldHostSubscriberId OBJECT-TYPE
    SYNTAX      TmnxSubIdentStringOrEmpty
    MAX-ACCESS  read-only
    STATUS      current
    DESCRIPTION
        "The value of vRtrMldHostSubscriberId indicates
         the subscriber identification of this subscriber host.
         
         This must be an existing subscriber."
    ::= { vRtrMldHostEntry 13 }

vRtrMldHostMldPolicy OBJECT-TYPE
    SYNTAX     TPolicyStatementNameOrEmpty
    MAX-ACCESS read-only
    STATUS     current
    DESCRIPTION
        "The value of vRtrMldHostMldPolicy specifies the name 
         of the MLD policy."
    DEFVAL { "" }
    ::= { vRtrMldHostEntry 14 }

vRtrMldHostMaxGroups OBJECT-TYPE
    SYNTAX     Unsigned32 (0|1..16000)
    MAX-ACCESS read-only
    STATUS     current
    DESCRIPTION
        "The value of vRtrMldHostMaxGroups specifies the maximum number of groups
         for which MLD can have local receiver information based on received
         MLD reports on this subscriber host.  When this configuration is changed 
         dynamically to a value lower than currently accepted number of groups,
         the groups that are already accepted are not deleted.  Only new groups 
         will not be allowed.  When this object has a value of 0, there is no 
         limit to the number of groups."
    DEFVAL { 0 }
    ::= { vRtrMldHostEntry 15 }

vRtrMldHostAdminVersion OBJECT-TYPE
    SYNTAX     TmnxMldVersion
    MAX-ACCESS read-only
    STATUS     current
    DESCRIPTION
        "The configured version of MLD which is running for this Host.
         For MLD to function correctly, all routers on a LAN must be configured
         to run the same version of MLD on that LAN."
    DEFVAL { version2 }
    ::= { vRtrMldHostEntry 16 }

vRtrMldHostMaxSources OBJECT-TYPE
    SYNTAX     Unsigned32 (0|1..1000)
    MAX-ACCESS read-only
    STATUS     current
    DESCRIPTION
        "The value of vRtrMldHostMaxSources specifies the maximum number of
         sources per group for which MLD can have local receiver information 
         based on received MLD reports on this subscriber host. When this 
         configuration is changed dynamically to a value lower than currently 
         accepted number of sources, the sources that are already accepted are
         not deleted. Only new sources will not be allowed. When this object has
         a value of 0, there is no limit to the number of sources."
    DEFVAL { 0 }
    ::= { vRtrMldHostEntry 17 }

vRtrMldHostMaxGrpSources OBJECT-TYPE
    SYNTAX     Unsigned32 (0|1..1000)
    MAX-ACCESS read-only
    STATUS     current
    DESCRIPTION
        "The value of vRtrMldHostMaxGrpSources specifies the maximum number of
         group sources per group for which MLD can have local receiver 
         information based on received MLD reports on this subscriber host.
         When this configuration is changed dynamically to a value lower than
         currently accepted number of sources, the sources that are already
         accepted are not deleted. Only new sources will not be allowed. When 
         this object has a value of 0, there is no limit to the number of
         sources."
    DEFVAL { 0 }
    ::= { vRtrMldHostEntry 18 }

vRtrMldHostQueryInterval OBJECT-TYPE
    SYNTAX     Unsigned32 (0|2..1024)
    UNITS      "seconds"
    MAX-ACCESS read-only
    STATUS     current
    DESCRIPTION
        "The value of vRtrMldHostQueryInterval indicates the frequency at 
         which the MLD Host-Query packets are transmitted on this subscriber
         host."
    ::= { vRtrMldHostEntry 19 }

vRtrMldHostLastLstnrQueryIntvl OBJECT-TYPE
    SYNTAX     Unsigned32 (0|1..1023)
    UNITS      "seconds"
    MAX-ACCESS read-only
    STATUS     current
    DESCRIPTION
        "The value of vRtrMldHostLastLstnrQueryIntvl indicates the Max Response 
         Time inserted into Group-Specific Queries sent in response to
         Leave Group messages, and is also the amount of time between
         Group-Specific Query messages.  This value may be tuned to
         modify the leave latency of the network.  A reduced value
         results in reduced time to detect the loss of the last
         member of a group."
    ::= { vRtrMldHostEntry 20 }

vRtrMldHostQueryResponseIntvl OBJECT-TYPE
    SYNTAX     Unsigned32 (0|1..1023)
    UNITS      "seconds"
    MAX-ACCESS read-only
    STATUS     current
    DESCRIPTION
        "The value of vRtrMldHostQueryResponseIntvl indicates 
         maximum query response time advertised in MLD v2 queries
         on this subscriber host."
    ::= { vRtrMldHostEntry 21 }

vRtrMldHostDisRtrAlertChk OBJECT-TYPE
     SYNTAX     TruthValue
     MAX-ACCESS read-only
     STATUS     current
     DESCRIPTION
         "vRtrMldHostDisRtrAlertChk indicates whether router alert checking
         for MLD messages is enabled or disabled.

         If this flag is set to 'true', checking is disabled." 
     ::= { vRtrMldHostEntry 22 }


--
--  The MLD Host Statistics Table
--

vRtrMldHostStatsTable OBJECT-TYPE
    SYNTAX     SEQUENCE OF VRtrMldHostStatsEntry
    MAX-ACCESS not-accessible
    STATUS     current
    DESCRIPTION
        "The table listing the MLD statistics for
         a particular host."
    ::= { vRtrMldHostObjs 2 }

vRtrMldHostStatsEntry OBJECT-TYPE
    SYNTAX     VRtrMldHostStatsEntry
    MAX-ACCESS not-accessible
    STATUS     current
    DESCRIPTION
        "An entry in the vRtrMldHostStatsTable."
    AUGMENTS      { vRtrMldHostEntry }
    ::= { vRtrMldHostStatsTable 1 }

VRtrMldHostStatsEntry ::= SEQUENCE {
    vRtrMldHostTxGenQueries         Counter32,
    vRtrMldHostTxGrpQueries         Counter32,
    vRtrMldHostTxGrpSrcQueries      Counter32,
    vRtrMldHostTxV1Reports          Counter32,
    vRtrMldHostTxV2Reports          Counter32,
    vRtrMldHostTxLeaves             Counter32,
    vRtrMldHostTxErrors             Counter32,
    vRtrMldHostRxGenQueries         Counter32,
    vRtrMldHostRxGrpQueries         Counter32,
    vRtrMldHostRxGrpSrcQueries      Counter32,
    vRtrMldHostRxV1Reports          Counter32,
    vRtrMldHostRxV2Reports          Counter32,
    vRtrMldHostRxLeaves             Counter32,
    vRtrMldHostRxBadLenPkts         Counter32,
    vRtrMldHostRxBadChecksumPkts    Counter32,
    vRtrMldHostRxUnknownTypePkts    Counter32,
    vRtrMldHostRxBadReceiveIfPkts   Counter32,
    vRtrMldHostRxNonLocal           Counter32,
    vRtrMldHostRxWrongVersions      Counter32,
    vRtrMldHostImportPolicyDrops    Counter32,
    vRtrMldHostRxNoRtrAlertPkts     Counter32,
    vRtrMldHostRxBadEncodings       Counter32,
    vRtrMldHostRxPktDrops           Counter32,
    vRtrMldHostStatsStarGTypes      Gauge32,
    vRtrMldHostStatsSGTypes         Gauge32,
    vRtrMldHostStatsMcacPolicyDrops Counter32,
    vRtrMldHostRxLocalScopePkts     Counter32,
    vRtrMldHostRxRsvdScopePkts      Counter32,
    vRtrMldHostRedirectionDrops     Counter32
}

vRtrMldHostTxGenQueries OBJECT-TYPE
    SYNTAX       Counter32
    MAX-ACCESS   read-only
    STATUS       current
    DESCRIPTION
        "The value of vRtrMldHostTxGenQueries indicates the number of MLD 
         General Queries transmitted for this host."
    ::= { vRtrMldHostStatsEntry 1 }

vRtrMldHostTxGrpQueries OBJECT-TYPE
    SYNTAX       Counter32
    MAX-ACCESS   read-only
    STATUS       current
    DESCRIPTION
        "The value of vRtrMldHostTxGrpQueries indicates the number of MLD 
         Group Specific Queries transmitted for this host."
    ::= { vRtrMldHostStatsEntry 2 }

vRtrMldHostTxGrpSrcQueries OBJECT-TYPE
    SYNTAX       Counter32
    MAX-ACCESS   read-only
    STATUS       current
    DESCRIPTION
        "The value of vRtrMldHostTxGrpSrcQueries indicates the number of MLD 
         Group and Source Specific Queries transmitted for this host."
    ::= { vRtrMldHostStatsEntry 3 }

vRtrMldHostTxV1Reports OBJECT-TYPE
    SYNTAX       Counter32
    MAX-ACCESS   read-only
    STATUS       current
    DESCRIPTION
        "The value of vRtrMldHostTxV1Reports indicates the total number of 
         MLD V1 Reports transmitted for this host."
    ::= { vRtrMldHostStatsEntry 4 }

vRtrMldHostTxV2Reports OBJECT-TYPE
    SYNTAX       Counter32
    MAX-ACCESS   read-only
    STATUS       current
    DESCRIPTION
        "The value of vRtrMldHostTxV2Reports indicates the total number of 
         MLD V2 Reports transmitted for this host."
    ::= { vRtrMldHostStatsEntry 5 }

vRtrMldHostTxLeaves OBJECT-TYPE
    SYNTAX       Counter32
    MAX-ACCESS   read-only
    STATUS       current
    DESCRIPTION
        "The value of vRtrMldHostTxLeaves indicates the total number of MLD
         Leaves transmitted for this host."
    ::= { vRtrMldHostStatsEntry 6 }

vRtrMldHostTxErrors OBJECT-TYPE
    SYNTAX       Counter32
    MAX-ACCESS   read-only
    STATUS       current
    DESCRIPTION
        "The value of vRtrMldHostTxErrors indicates the total number of times
         there was an error transmitting MLD packets for this host."
    ::= { vRtrMldHostStatsEntry 7 }

vRtrMldHostRxGenQueries OBJECT-TYPE
    SYNTAX       Counter32
    MAX-ACCESS   read-only
    STATUS       current
    DESCRIPTION
        "The value of vRtrMldHostRxGenQueries indicates the total number of MLD 
         General Queries received for this host."
    ::= { vRtrMldHostStatsEntry 8 }

vRtrMldHostRxGrpQueries OBJECT-TYPE
    SYNTAX       Counter32
    MAX-ACCESS   read-only
    STATUS       current
    DESCRIPTION
        "The value of vRtrMldHostRxGrpQueries indicates the number of MLD 
         Group Specific Queries received for this host."
    ::= { vRtrMldHostStatsEntry 9 }

vRtrMldHostRxGrpSrcQueries OBJECT-TYPE
    SYNTAX       Counter32
    MAX-ACCESS   read-only
    STATUS       current
    DESCRIPTION
        "The value of vRtrMldHostRxGrpSrcQueries indicates the number of MLD 
         Group and Source Specific Queries received for this host."
    ::= { vRtrMldHostStatsEntry 10 }

vRtrMldHostRxV1Reports OBJECT-TYPE
    SYNTAX       Counter32
    MAX-ACCESS   read-only
    STATUS       current
    DESCRIPTION
        "The value of vRtrMldHostRxV1Reports indicates the total number of 
         MLD V1 Reports received for this host."
    ::= { vRtrMldHostStatsEntry 11 }

vRtrMldHostRxV2Reports OBJECT-TYPE
    SYNTAX       Counter32
    MAX-ACCESS   read-only
    STATUS       current
    DESCRIPTION
        "The value of vRtrMldHostRxV2Reports indicates the total number of 
         MLD V2 Reports received for this host."
    ::= { vRtrMldHostStatsEntry 12 }

vRtrMldHostRxLeaves OBJECT-TYPE
    SYNTAX       Counter32
    MAX-ACCESS   read-only
    STATUS       current
    DESCRIPTION
        "The value of vRtrMldHostRxLeaves indicates the total number of 
         MLD Leaves received for this host."
    ::= { vRtrMldHostStatsEntry 13 }

vRtrMldHostRxBadLenPkts OBJECT-TYPE
    SYNTAX       Counter32
    MAX-ACCESS   read-only
    STATUS       current
    DESCRIPTION
        "The value of vRtrMldHostRxBadLenPkts indicates the total number of 
    MLD packets with bad length received for this host."
    ::= { vRtrMldHostStatsEntry 14 }

vRtrMldHostRxBadChecksumPkts OBJECT-TYPE
    SYNTAX       Counter32
    MAX-ACCESS   read-only
    STATUS       current
    DESCRIPTION
        "The value of vRtrMldHostRxBadChecksumPkts indicates the total number of 
         MLD packets with bad checksum received for this host."
    ::= { vRtrMldHostStatsEntry 15 }

vRtrMldHostRxUnknownTypePkts OBJECT-TYPE
    SYNTAX       Counter32
    MAX-ACCESS   read-only
    STATUS       current
    DESCRIPTION
        "The value of vRtrMldHostRxUnknownTypePkts indicates the total number of 
         MLD packets with unknown type received for this host."
    ::= { vRtrMldHostStatsEntry 16 }

vRtrMldHostRxBadReceiveIfPkts OBJECT-TYPE
    SYNTAX       Counter32
    MAX-ACCESS   read-only
    STATUS       current
    DESCRIPTION
        "The value of vRtrMldHostRxBadReceiveIfPkts indicates the total 
         number of MLD packets incorrectly received for this host."
    ::= { vRtrMldHostStatsEntry 17 }

vRtrMldHostRxNonLocal OBJECT-TYPE
    SYNTAX       Counter32
    MAX-ACCESS   read-only
    STATUS       current
    DESCRIPTION
        "The value of vRtrMldHostRxNonLocal indicates the total number of 
    MLD packets received from a non-local sender."
    ::= { vRtrMldHostStatsEntry 18 }

vRtrMldHostRxWrongVersions OBJECT-TYPE
    SYNTAX       Counter32
    MAX-ACCESS   read-only
    STATUS       current
    DESCRIPTION
        "The value of vRtrMldHostRxWrongVersions indicates the total number of 
         MLD packets with wrong versions received for this host."
    ::= { vRtrMldHostStatsEntry 19 }

vRtrMldHostImportPolicyDrops OBJECT-TYPE
    SYNTAX       Counter32
    MAX-ACCESS   read-only
    STATUS       current
    DESCRIPTION
        "The value of vRtrMldHostImportPolicyDrops indicates the total number of 
         times MLD protocol instance matched the host IP address or 
         group/source addresses specified in the import policy."
    ::= { vRtrMldHostStatsEntry 20 }

vRtrMldHostRxNoRtrAlertPkts OBJECT-TYPE
    SYNTAX       Counter32
    MAX-ACCESS   read-only
    STATUS       current
    DESCRIPTION
        "The value of vRtrMldHostRxNoRtrAlertPkts indicates the total number of 
         MLDv2 packets received for this host which did not have the 
         router alert flag set."
    ::= { vRtrMldHostStatsEntry 21 }

vRtrMldHostRxBadEncodings OBJECT-TYPE
    SYNTAX       Counter32
    MAX-ACCESS   read-only
    STATUS       current
    DESCRIPTION
        "The value of vRtrMldHostRxBadEncodings indicates the total number of 
         MLD packets received for this host which were not encoded
         correctly."
    ::= { vRtrMldHostStatsEntry 22 }

vRtrMldHostRxPktDrops OBJECT-TYPE
    SYNTAX       Counter32
    MAX-ACCESS   read-only
    STATUS       current
    DESCRIPTION
        "The value of vRtrMldHostRxPktDrops indicates the total number of 
         MLD packets that were received for this host but were dropped."
    ::= { vRtrMldHostStatsEntry 23 }

vRtrMldHostStatsStarGTypes OBJECT-TYPE
    SYNTAX       Gauge32
    MAX-ACCESS   read-only
    STATUS       current
    DESCRIPTION
        "vRtrMldHostStatsStarGTypes indicates the number of entries for this 
         host for which the source type is 'starG'."
    ::= { vRtrMldHostStatsEntry 24 }

vRtrMldHostStatsSGTypes OBJECT-TYPE
    SYNTAX       Gauge32
    MAX-ACCESS   read-only
    STATUS       current
    DESCRIPTION
        "The value of vRtrMldHostStatsSGTypes indicates the number of entries 
         for this host for which the source type is 'sg'."
    ::= { vRtrMldHostStatsEntry 25 }

vRtrMldHostStatsMcacPolicyDrops OBJECT-TYPE
    SYNTAX       Counter32
    MAX-ACCESS   read-only
    STATUS       current
    DESCRIPTION
        "The value of the object vRtrMldHostStatsMcacPolicyDrops indicates 
         the number times an MLD Group is dropped because of applying a
         multicast CAC policy for this host."
    ::= { vRtrMldHostStatsEntry 26 }

vRtrMldHostRxLocalScopePkts OBJECT-TYPE
    SYNTAX       Counter32
    MAX-ACCESS   read-only
    STATUS       current
    DESCRIPTION
        "The value of the object vRtrMldHostRxLocalScopePkts indicates 
         the number of MLD packets received on the link-local scope IPv4 
         multicast address."
    ::= { vRtrMldHostStatsEntry 27 }

vRtrMldHostRxRsvdScopePkts OBJECT-TYPE
    SYNTAX       Counter32
    MAX-ACCESS   read-only
    STATUS       current
    DESCRIPTION
        "The value of the object vRtrMldHostRxRsvdScopePkts indicates 
         the number of MLD packets received on the reserved scope IPv4
         multicast address."
    ::= { vRtrMldHostStatsEntry 28 }

vRtrMldHostRedirectionDrops OBJECT-TYPE
    SYNTAX       Counter32
    MAX-ACCESS   read-only
    STATUS       current
    DESCRIPTION
        "The value of the object vRtrMldHostRedirectionDrops indicates 
         the number times an MLD Group is dropped because of a failure 
         while applying a redirection policy for this host."
    ::= { vRtrMldHostStatsEntry 29 }

--
--  The MLD Group Interface Table
--

vRtrMldGrpIfTable OBJECT-TYPE
    SYNTAX     SEQUENCE OF VRtrMldGrpIfEntry
    MAX-ACCESS not-accessible
    STATUS     current
    DESCRIPTION
        "The table listing the group interfaces on which MLD protocol
         operation is enabled."
    ::= { vRtrMldHostObjs 3 }

vRtrMldGrpIfEntry OBJECT-TYPE
    SYNTAX     VRtrMldGrpIfEntry
    MAX-ACCESS not-accessible
    STATUS     current
    DESCRIPTION
        "Each row entry in the vRtrMldGrpIfTable represents a group interface on
         this router that participates in the MLD protocol.  An entry in
         this table can be created or destroyed by an SNMP SET request to
         vRtrMldGrpIfRowStatus. An attempt to destroy a row will fail if
         vRtrMldGrpIfAdminState has not first been set to 'outOfService'."
    INDEX      { vRtrID,
                 vRtrIfFwdSvcId,
                 vRtrIfIndex }
    ::= { vRtrMldGrpIfTable 1 }

VRtrMldGrpIfEntry ::= SEQUENCE {
    vRtrMldGrpIfRowStatus           RowStatus,
    vRtrMldGrpIfLastChangeTime      TimeStamp,
    vRtrMldGrpIfAdminState          TmnxAdminState,
    vRtrMldGrpIfOperState           TmnxOperState,
    vRtrMldGrpIfSubHostsOnly        TruthValue,                                                        
    vRtrMldGrpIfAdminVersion        TmnxMldVersion,
    vRtrMldGrpIfImportPolicy        TPolicyStatementNameOrEmpty,
    vRtrMldGrpIfSubnetCheck         TruthValue,
    vRtrMldGrpIfMcacPolicyName      TPolicyStatementNameOrEmpty,
    vRtrMldGrpIfMcacUnconstrainedBW Integer32,
    vRtrMldGrpIfMcacConstAdminState TmnxAdminState,
    vRtrMldGrpIfMcacPreRsvdMandBW   Integer32,
    vRtrMldGrpIfMcacinUseMandBw     Unsigned32, 
    vRtrMldGrpIfMcacinUseOpnlBw     Unsigned32, 
    vRtrMldGrpIfMcacAvailMandBw     Unsigned32, 
    vRtrMldGrpIfMcacAvailOpnlBw     Unsigned32,
    vRtrMldGrpIfMcacValuesInTransit TruthValue,                                                        
    vRtrMldGrpIfDisRtrAlertChk      TruthValue,
    vRtrMldGrpIfMaxGroups           Unsigned32,
    vRtrMldGrpIfMaxSources          Unsigned32,
    vRtrMldGrpIfMaxGrpSources       Unsigned32,
    vRtrMldGrpIfQrySrcIpAddrType    InetAddressType,   
    vRtrMldGrpIfQrySrcIpAddr        InetAddress,   
    vRtrMldGrpIfMcacIfPolicyName           TPolicyStatementNameOrEmpty,
    vRtrMldGrpIfQueryInterval              Unsigned32,
    vRtrMldGrpIfLastLstnrQueryIntvl        Unsigned32,
    vRtrMldGrpIfQueryResponseIntvl         Unsigned32
}

vRtrMldGrpIfRowStatus OBJECT-TYPE
    SYNTAX     RowStatus
    MAX-ACCESS read-create
    STATUS     current
    DESCRIPTION
        "The activation of a row enables MLD on the group interface. The
         destruction of a row disables MLD on the group interface. Before 
         this row can be destroyed, vRtrMldGrpIfAdminState must have been 
         set to 'outOfService'."
    ::= { vRtrMldGrpIfEntry 1 }

vRtrMldGrpIfLastChangeTime       OBJECT-TYPE
    SYNTAX      TimeStamp
    MAX-ACCESS  read-only
    STATUS      current
    DESCRIPTION
        "The sysUpTime when this row was last modified."
    ::= { vRtrMldGrpIfEntry 2 }

vRtrMldGrpIfAdminState       OBJECT-TYPE
    SYNTAX      TmnxAdminState
    MAX-ACCESS  read-create
    STATUS      current
    DESCRIPTION
        "vRtrMldGrpIfAdminState specifies the desired administrative state 
         for MLD protocol on this group interface."
    DEFVAL { inService }
    ::= { vRtrMldGrpIfEntry 3 }

vRtrMldGrpIfOperState        OBJECT-TYPE
    SYNTAX      TmnxOperState
    MAX-ACCESS  read-only
    STATUS      current
    DESCRIPTION
        "The current operational state of MLD protocol on this group interface."
    ::= { vRtrMldGrpIfEntry 4 }

    
vRtrMldGrpIfSubHostsOnly OBJECT-TYPE
     SYNTAX     TruthValue
     MAX-ACCESS read-create
     STATUS     current
     DESCRIPTION
         "vRtrMldGrpIfSubHostsOnly is used to enable/disable handling of 
     MLD joins received from hosts that are not known in subscriber
          management or on which no MLD policy is applied.
          
          If this flag is set to 'true', only traffic from MLD enabled
          hosts is allowed." 
     DEFVAL     { true }
     ::= { vRtrMldGrpIfEntry 5 }

vRtrMldGrpIfAdminVersion OBJECT-TYPE
    SYNTAX     TmnxMldVersion
    MAX-ACCESS read-create
    STATUS     current
    DESCRIPTION
        "The configured version of MLD which is running on SAPs belonging
         to this group-interface.
         
         This object can be used to configure a router capable of
         running either value.  For MLD to function correctly, all
         routers on a LAN must be configured to run the same version
         of MLD on that LAN."
     DEFVAL { version2 }
     ::= { vRtrMldGrpIfEntry 6 }

vRtrMldGrpIfImportPolicy OBJECT-TYPE
    SYNTAX     TPolicyStatementNameOrEmpty
    MAX-ACCESS read-create
    STATUS     current
    DESCRIPTION
        "vRtrMldGrpIfImportPolicy specifies the policy that is to be applied
         on SAPs belonging to this group-interface."
    DEFVAL { ''H }
    ::= { vRtrMldGrpIfEntry 7 }

vRtrMldGrpIfSubnetCheck OBJECT-TYPE
    SYNTAX     TruthValue
    MAX-ACCESS read-create
    STATUS     current
    DESCRIPTION
        "vRtrMldGrpIfSubnetCheck is used to enable/disable subnet
        checking for MLD messages received on SAPs belonging to this
        group-interface.

        If this flag is set to 'true', subnet checking is enabled. 
        All MLD packets with a source address that is not in 
        the local subnet are dropped." 
    DEFVAL     { true }
    ::= { vRtrMldGrpIfEntry 8 }

vRtrMldGrpIfMcacPolicyName OBJECT-TYPE
    SYNTAX     TPolicyStatementNameOrEmpty
    MAX-ACCESS read-create
    STATUS     current
    DESCRIPTION
        "The value of vRtrMldGrpIfMcacPolicyName specifies the name 
         of the multicast CAC policy.

         The multicast CAC policy applies to the group-interface CAC algorithm
         if the channel(group) on SAPs belonging to this group-interface is part
         of the policy as specified in vRtrMldGrpIfMcacPolicyName."
    DEFVAL { "" }
    ::= { vRtrMldGrpIfEntry 9 }

vRtrMldGrpIfMcacUnconstrainedBW OBJECT-TYPE
    SYNTAX      Integer32 (-1|0..2147483647)
    UNITS       "kbps"
    MAX-ACCESS  read-create
    STATUS      current
    DESCRIPTION
        "The value of vRtrMldGrpIfMcacUnconstrainedBW specifies the bandwidth
         assigned for all SAPs belonging to this group-interface's multicast
         CAC policy traffic in kilo-bits per second(kbps). 
         
         If the default value of '-1' is set, there is no constraint on bandwidth 
         allocated to the group-interface. 
         
         If the value of vRtrMldGrpIfMcacUnconstrainedBW is set to '0' and if 
         a multicast CAC policy is assigned on the group-interface, then 
         no group (channel) from that policy is allowed on a SAP belonging to
         that group-interface."
    DEFVAL { -1 }
    ::= { vRtrMldGrpIfEntry 10 }

vRtrMldGrpIfMcacConstAdminState OBJECT-TYPE
    SYNTAX      TmnxAdminState
    MAX-ACCESS  read-create
    STATUS      current
    DESCRIPTION
        "The value of vRtrMldGrpIfMcacConstAdminState specifies the 
         administrative state of the multicast CAC policy's constraints."
    DEFVAL { inService } 
    ::= { vRtrMldGrpIfEntry 11 }     

vRtrMldGrpIfMcacPreRsvdMandBW OBJECT-TYPE
    SYNTAX      Integer32 (-1|0..2147483647)
    UNITS       "kbps"
    MAX-ACCESS  read-create
    STATUS      current
    DESCRIPTION
        "The value of vRtrMldGrpIfMcacPreRsvdMandBW specifies the bandwidth
         pre-reserved for all the mandatory channels on all SAPs belonging 
         to a given group-interface in kilo-bits per second(kbps). 
              
         If the value of vRtrMldGrpIfMcacUnconstrainedBW is '0', no mandatory
         channels are allowed. If the value of vRtrMldGrpIfMcacUnconstrainedBW 
         is '-1', then all mandatory and optional channels are allowed.

         If the value of vRtrMldGrpIfMcacPreRsvdMandBW is equal to the value of
         vRtrMldGrpIfMcacUnconstrainedBW, then all the unconstrained bandwidth
         on all SAPs belonging to a given group-interface is allocated to
         mandatory channels configured through multicast CAC policy on that 
         group-interface and no optional groups (channels) are allowed.

         The value of vRtrMldGrpIfMcacPreRsvdMandBW should always be less than
         or equal to that of vRtrMldGrpIfMcacUnconstrainedBW. An attempt to set
         the value of vRtrMldGrpIfMcacPreRsvdMandBW greater than that of 
         vRtrMldGrpIfMcacUnconstrainedBW will result in inconsistent value error."
    DEFVAL { -1 }
    ::= { vRtrMldGrpIfEntry 12 }

vRtrMldGrpIfMcacinUseMandBw  OBJECT-TYPE
    SYNTAX     Unsigned32
    UNITS      "kbps"
    MAX-ACCESS read-only
    STATUS     current
    DESCRIPTION
        "The value of vRtrMldGrpIfMcacinUseMandBw indicates the 
         in-use bandwidth in kilo-bits per second(kbps) for the 
         mandatory channels for all SAPs belonging to this protocol
         group-interface instance."
    ::= { vRtrMldGrpIfEntry 13 }

vRtrMldGrpIfMcacinUseOpnlBw  OBJECT-TYPE
    SYNTAX     Unsigned32
    UNITS      "kbps"
    MAX-ACCESS read-only
    STATUS     current
    DESCRIPTION
        "The value of vRtrMldGrpIfMcacinUseOpnlBw indicates the 
         in-use bandwidth in kilo-bits per second(kbps) for the 
         optional channels for all SAPs belonging to this protocol 
         group-interface instance."
    ::= { vRtrMldGrpIfEntry 14 }

vRtrMldGrpIfMcacAvailMandBw  OBJECT-TYPE
    SYNTAX     Unsigned32
    UNITS      "kbps"
    MAX-ACCESS read-only
    STATUS     current
    DESCRIPTION
        "The value of vRtrMldGrpIfMcacAvailMandBw indicates the 
         pre-reserved bandwidth in kilo-bits per second(kbps) 
         for the mandatory channels for all SAPs belonging to this 
         group-interface instance."
    ::= { vRtrMldGrpIfEntry 15 }

vRtrMldGrpIfMcacAvailOpnlBw  OBJECT-TYPE
    SYNTAX     Unsigned32
    UNITS      "kbps"
    MAX-ACCESS read-only
    STATUS     current
    DESCRIPTION
        "The value of vRtrMldGrpIfMcacAvailOpnlBw indicates the 
         available bandwidth in kilo-bits per second(kbps) for all SAPs
         belonging to this group-interface instance."
    ::= { vRtrMldGrpIfEntry 16 }

vRtrMldGrpIfMcacValuesInTransit   OBJECT-TYPE
    SYNTAX      TruthValue
    MAX-ACCESS  read-only
    STATUS      current
    DESCRIPTION
        "The value of vRtrMldGrpIfMcacValuesInTransit indicates that the
         operational (available and in-use mandatory/optional) value for the 
         following objects are in transition due to configuration change:

         vRtrMldGrpIfMcacAvailMandBw
         vRtrMldGrpIfMcacAvailOpnlBw
         vRtrMldGrpIfMcacinUseMandBw
         vRtrMldGrpIfMcacinUseOpnlBw

         When Multicast CAC Policy is applied on the group-interface for the 
         join of the next channel, the operational values will be recalculated
         and applied to the above objects and the value for
         vRtrMldGrpIfMcacValuesInTransit will be set to 'false'.

         If the value of vRtrMldGrpIfMcacValuesInTransit is 'true' then the
         values are in transition."
    ::= { vRtrMldGrpIfEntry 17 }

vRtrMldGrpIfDisRtrAlertChk OBJECT-TYPE
     SYNTAX     TruthValue
     MAX-ACCESS read-create
     STATUS     current
     DESCRIPTION
         "vRtrMldGrpIfDisRtrAlertChk is used to enable/disable router
         alert checking for MLD messages received on SAPs belonging to 
         this group-interface.

         If this flag is set to 'true', checking is disabled." 
     DEFVAL     { false }
     ::= { vRtrMldGrpIfEntry 18 }

vRtrMldGrpIfMaxGroups OBJECT-TYPE
    SYNTAX     Unsigned32 (0|1..16000)
    MAX-ACCESS read-create
    STATUS     current
    DESCRIPTION
        "The value of vRtrMldGrpIfMaxGroups specifies the maximum number of groups
         for which MLD can have local receiver information based on received
         MLD reports on a SAP belonging to this group-interface.  When this 
         configuration is changed dynamically to a value lower than currently
         accepted number of groups, the groups that are already accepted are not
         deleted. Only new groups will not be allowed. When this object has a 
         value of 0, there is no limit to the number of groups."
    DEFVAL { 0 }
    ::= { vRtrMldGrpIfEntry 19 }

vRtrMldGrpIfMaxSources OBJECT-TYPE
    SYNTAX     Unsigned32 (0|1..1000)
    MAX-ACCESS read-create
    STATUS     current
    DESCRIPTION
        "The value of vRtrMldGrpIfMaxSources specifies the maximum number of sources
         for which MLD can have local receiver information based on received
         MLD reports on a SAP belonging to this group-interface.  When this 
         configuration is changed dynamically to a value lower than currently
         accepted number of sources, the sources that are already accepted are not
         deleted. Only new sources will not be allowed. When this object has a 
         value of 0, there is no limit to the number of sources."
    DEFVAL { 0 }
    ::= { vRtrMldGrpIfEntry 20 }

vRtrMldGrpIfMaxGrpSources OBJECT-TYPE
    SYNTAX     Unsigned32 (0|1..32000)
    MAX-ACCESS read-create
    STATUS     current
    DESCRIPTION
        "The value of vRtrMldGrpIfMaxGrpSources specifies the maximum number of
         group sources for which MLD can have local receiver information based 
         on received MLD reports on a SAP belonging to this group-interface.  
         When this configuration is changed dynamically to a value lower than
         currently accepted number of group sources, the group sources that are
         already accepted are not deleted. Only new group sources will not be
         allowed. When this object has a value of 0, there is no limit to the
         number of group sources."
    DEFVAL { 0 }
    ::= { vRtrMldGrpIfEntry 21 }

vRtrMldGrpIfQrySrcIpAddrType OBJECT-TYPE
    SYNTAX     InetAddressType
    MAX-ACCESS read-create
    STATUS     current
    DESCRIPTION
        "The value of vRtrMldGrpIfQrySrcIpAddrType indicates the type of 
         address to be used for vRtrMldGrpIfQrySrcIpAddr."         
    ::= { vRtrMldGrpIfEntry 22 }

vRtrMldGrpIfQrySrcIpAddr OBJECT-TYPE
    SYNTAX     InetAddress (SIZE(0|16))
    MAX-ACCESS read-create
    STATUS     current
    DESCRIPTION
        "The value of vRtrMldGrpIfQrySrcIpAddr specifies the source IP  
         address used when generating MLD queries on group interfaces."
    ::= { vRtrMldGrpIfEntry 23 }

vRtrMldGrpIfMcacIfPolicyName OBJECT-TYPE
    SYNTAX     TPolicyStatementNameOrEmpty
    MAX-ACCESS read-create
    STATUS     current
    DESCRIPTION
        "The value of vRtrMldGrpIfMcacIfPolicyName specifies the name 
         of the multicast CAC interface policy.

         The multicast CAC policy applies to the group-interface CAC algorithm
         if the channel(group) on SAPs belonging to this group-interface is part
         of the policy as specified in vRtrMldGrpIfMcacIfPolicyName."
    DEFVAL { "" }
    ::= { vRtrMldGrpIfEntry 24 }

vRtrMldGrpIfQueryInterval OBJECT-TYPE
    SYNTAX     Unsigned32 (0|2..1024)
    UNITS      "seconds"
    MAX-ACCESS read-create
    STATUS     current
    DESCRIPTION
        "The value of vRtrMldGrpIfQueryInterval specifies the frequency at 
         which the MLD Host-Query packets are transmitted on this interface."
    DEFVAL { 0 }
    ::= { vRtrMldGrpIfEntry 25 }

vRtrMldGrpIfLastLstnrQueryIntvl OBJECT-TYPE
    SYNTAX     Unsigned32 (0|1..1023)
    UNITS      "seconds"
    MAX-ACCESS read-create
    STATUS     current
    DESCRIPTION
        "The value of vRtrMldGrpIfLastLstnrQueryIntvl specifies the Max Response 
         Time inserted into Group-Specific Queries sent in response to
         Leave Group messages, and is also the amount of time between
         Group-Specific Query messages.  This value may be tuned to
         modify the leave latency of the network.  A reduced value
         results in reduced time to detect the loss of the last
         member of a group."
    DEFVAL { 0 }
    ::= { vRtrMldGrpIfEntry 26 }

vRtrMldGrpIfQueryResponseIntvl OBJECT-TYPE
    SYNTAX     Unsigned32 (0|1..1023)
    UNITS      "seconds"
    MAX-ACCESS read-create
    STATUS     current
    DESCRIPTION
        "The value of vRtrMldGrpIfQueryResponseIntvl specifies 
         maximum query response time advertised in MLD v2 queries
         on this interface."
    DEFVAL { 0 }
    ::= { vRtrMldGrpIfEntry 27 }

--
--  The MLD Group Interface Host Group Table
--

vRtrMldGrpIfHostGrpTable OBJECT-TYPE
    SYNTAX     SEQUENCE OF VRtrMldGrpIfHostGrpEntry
    MAX-ACCESS not-accessible
    STATUS     current
    DESCRIPTION
        "The table listing the IP multicast groups for
         which there are members on a particular host. This table 
         represents the MLD group database."
    ::= { vRtrMldHostObjs 4 }

vRtrMldGrpIfHostGrpEntry OBJECT-TYPE
    SYNTAX     VRtrMldGrpIfHostGrpEntry
    MAX-ACCESS not-accessible
    STATUS     current
    DESCRIPTION
        "An entry in the vRtrMldGrpIfHostGrpTable. Each entry represents a 
         group address for which receivers are
         interested/not interested in receiving multicast traffic."
    INDEX      { vRtrID, 
                 vRtrIfFwdSvcId,
                 vRtrGrpIfIndex, 
                 vRtrMldHostAddressType,
                 vRtrMldHostAddress,
                 vRtrMldHostMacAddress,
                 vRtrMldHostPppoeSessionId,
                 vRtrMldHostGroupAddressType,
                 vRtrMldHostGroupAddress }
    ::= { vRtrMldGrpIfHostGrpTable 1 }

VRtrMldGrpIfHostGrpEntry ::= SEQUENCE {
    vRtrMldHostGroupAddressType      InetAddressType,
    vRtrMldHostGroupAddress          InetAddress,
    vRtrMldGrpIfHostGrpType          TmnxMldGroupType,
    vRtrMldGrpIfHostGrpUpTime        TimeInterval,
    vRtrMldGrpIfHostGrpExpiryTime    TimeInterval,
    vRtrMldGrpIfHostGrpVer1HostTmr   TimeInterval,
    vRtrMldGrpIfHostGrpMode          TmnxMldGroupFilterMode,
    vRtrMldGrpIfHostGrpCompatMode    TmnxMldVersion,
    vRtrMldGrpIfHostGrpMRDstVrId     TmnxVRtrIDOrZero,
    vRtrMldGrpIfHostGrpMRDstIfId     InterfaceIndexOrZero
}

vRtrMldHostGroupAddressType OBJECT-TYPE
    SYNTAX     InetAddressType
    MAX-ACCESS not-accessible
    STATUS     current
    DESCRIPTION
        "The value of vRtrMldHostGroupAddressType indicates the type of 
         address to be used for vRtrMldHostGroupAddress."         
    ::= { vRtrMldGrpIfHostGrpEntry 1 }

vRtrMldHostGroupAddress OBJECT-TYPE
    SYNTAX     InetAddress (SIZE(16))
    MAX-ACCESS not-accessible
    STATUS     current
    DESCRIPTION
        "The IP multicast group address for which this entry
         contains information."
    ::= { vRtrMldGrpIfHostGrpEntry 2 }

vRtrMldGrpIfHostGrpType OBJECT-TYPE
    SYNTAX     TmnxMldGroupType
    MAX-ACCESS read-only
    STATUS     current
    DESCRIPTION
        "vRtrMldGrpIfHostGrpType indicates how this group entry was learned. 
         If this group entry was learned by MLD, it will be set to 'dynamic'. 
         For statically configured groups, the value will be set to 'static'."
    ::= { vRtrMldGrpIfHostGrpEntry 3 }

vRtrMldGrpIfHostGrpUpTime OBJECT-TYPE
    SYNTAX     TimeInterval
    MAX-ACCESS read-only
    STATUS     current
    DESCRIPTION
        "The time elapsed since this entry was created."
    ::= { vRtrMldGrpIfHostGrpEntry 4 }

vRtrMldGrpIfHostGrpExpiryTime OBJECT-TYPE
    SYNTAX     TimeInterval
    MAX-ACCESS read-only
    STATUS     current
    DESCRIPTION
        "The value of vRtrMldGrpIfHostGrpExpiryTime indicates the minimum amount 
         of time remaining before this entry will be aged out.

         If the value of vRtrMldGrpIfHostGrpType is 'static', the value of 
         vRtrMldGrpIfHostGrpExpiryTime will be set to maximum,
         which is 2147483647." 
    ::= { vRtrMldGrpIfHostGrpEntry 5 }

vRtrMldGrpIfHostGrpVer1HostTmr OBJECT-TYPE
    SYNTAX     TimeInterval
    MAX-ACCESS read-only
    STATUS     current
    DESCRIPTION
        "The time remaining until the local router will assume that
         there are no longer any MLD version 1 members on the IP
         subnet attached to this host.  Upon hearing any MLDv1
         Membership Report, this value is reset to the group
         membership timer.  While this time remaining is non-zero,
         the local router ignores any MLDv1 Done messages for this
         group that it receives on this host."
    ::= { vRtrMldGrpIfHostGrpEntry 6 }

vRtrMldGrpIfHostGrpMode OBJECT-TYPE
    SYNTAX     TmnxMldGroupFilterMode
    MAX-ACCESS read-only
    STATUS     current
    DESCRIPTION
        "vRtrMldGrpIfHostGrpMode is based on the type of membership report(s) 
         received on the host for the group. In the 'include' mode, 
         reception of packets sent to the specified multicast address is 
         requested only from those IP source addresses listed in the 
         source-list parameter of the MLD membership report. 
         In 'exclude' mode, reception of packets sent to the given multicast 
         address is requested from all IP source addresses except those listed 
         in the source-list parameter.
         vRtrMldGrpIfHostGrpSrcTable lists the sources corresponding to this group,
         if any."
    ::= { vRtrMldGrpIfHostGrpEntry 7 }

vRtrMldGrpIfHostGrpCompatMode OBJECT-TYPE
    SYNTAX     TmnxMldVersion 
    MAX-ACCESS read-only
    STATUS     current
    DESCRIPTION
        "vRtrMldGrpIfHostGrpCompatMode is used in order for routers to be 
         compatible with older version routers. MLDv2 hosts MUST operate 
         in version 1 and version 2 compatibility modes.  MLDv2 hosts MUST 
         keep state per local host regarding the compatibility mode of 
         each attached network.  A host's compatibility mode is determined 
         from the Host Compatibility Mode variable which can be in
         one of two states: MLDv1 or MLDv2.  This variable is
         kept per interface and is dependent on the version of General Queries
         heard on that host as well as the Older Version Querier Present
         timers for the host."
    ::= { vRtrMldGrpIfHostGrpEntry 8 }

vRtrMldGrpIfHostGrpMRDstVrId   OBJECT-TYPE
    SYNTAX       TmnxVRtrIDOrZero
    MAX-ACCESS   read-only
    STATUS       current
    DESCRIPTION  
        "The value of vRtrMldGrpIfHostGrpMRDstVrId indicates the vRtrID of 
         the service where to redirect MLD multicast traffic to.
 
         The value zero means that no multicast redirection is configured."
    ::= { vRtrMldGrpIfHostGrpEntry 9 }

vRtrMldGrpIfHostGrpMRDstIfId  OBJECT-TYPE
    SYNTAX      InterfaceIndexOrZero
    MAX-ACCESS  read-only
    STATUS      current
    DESCRIPTION
        "The value of vRtrMldGrpIfHostGrpMRDstIfId indicates the interface 
         index of the interface where to redirect MLD multicast traffic to.
 
         The value zero means that no multicast redirection is configured."
    ::= { vRtrMldGrpIfHostGrpEntry 10 }


--
--  The MLD Group Interface Host Group Source Table
--

vRtrMldGrpIfHostGrpSrcTable OBJECT-TYPE
    SYNTAX     SEQUENCE OF VRtrMldGrpIfHostGrpSrcEntry
    MAX-ACCESS not-accessible
    STATUS     current
    DESCRIPTION
        "The table listing the IP multicast sources
         corresponding to the IP multicast groups for which there 
         are members on a particular host. This table represents
         MLD source, group database."
    ::= { vRtrMldHostObjs 5 }

vRtrMldGrpIfHostGrpSrcEntry OBJECT-TYPE
    SYNTAX     VRtrMldGrpIfHostGrpSrcEntry
    MAX-ACCESS not-accessible
    STATUS     current
    DESCRIPTION
        "An entry in the vRtrMldGrpIfHostGrpSrcTable. 
         Each entry represents a source address from which receivers are
         interested/not interested in receiving multicast traffic from. 
         "
    INDEX      { vRtrID,
                 vRtrIfFwdSvcId,
                 vRtrGrpIfIndex,
                 vRtrMldHostAddressType,
                 vRtrMldHostAddress,
                 vRtrMldHostMacAddress,
                 vRtrMldHostPppoeSessionId,
                 vRtrMldHostGroupAddressType,
                 vRtrMldHostGroupAddress, 
                 vRtrMldHostGrpSrcAddressType,
                 vRtrMldHostGrpSrcAddress }
    ::= { vRtrMldGrpIfHostGrpSrcTable 1 }

VRtrMldGrpIfHostGrpSrcEntry ::= SEQUENCE {
    vRtrMldHostGrpSrcAddressType    InetAddressType,
    vRtrMldHostGrpSrcAddress        InetAddress,
    vRtrMldGrpIfHostGrpSrcExpTime   TimeInterval,
    vRtrMldGrpIfHostGrpSrcType      TmnxMldGroupType,
    vRtrMldGrpIfHostGrpSrcMRDstVrId TmnxVRtrIDOrZero,
    vRtrMldGrpIfHostGrpSrcMRDstIfId InterfaceIndexOrZero
}

vRtrMldHostGrpSrcAddressType OBJECT-TYPE
    SYNTAX     InetAddressType
    MAX-ACCESS not-accessible
    STATUS     current
    DESCRIPTION
        "The value of vRtrMldHostGrpSrcAddressType indicates the type of 
         address to be used for vRtrMldHostGrpSrcAddress."         
    ::= { vRtrMldGrpIfHostGrpSrcEntry 1 }

vRtrMldHostGrpSrcAddress OBJECT-TYPE
    SYNTAX     InetAddress (SIZE(16))
    MAX-ACCESS not-accessible
    STATUS     current
    DESCRIPTION
        "The address of the source sending multicast traffic to the group
         identified by vRtrMldHostGroupAddress."
    ::= { vRtrMldGrpIfHostGrpSrcEntry 2 }

vRtrMldGrpIfHostGrpSrcExpTime OBJECT-TYPE
    SYNTAX     TimeInterval
    MAX-ACCESS read-only
    STATUS     current
    DESCRIPTION
        "The minimum amount of time remaining before this entry will be aged out.
         If the value of vRtrMldGrpIfHostGrpSrcExpTime is non-zero and the 
         value of vRtrMldGrpIfHostGrpMode corresponding to this entry is 'include',
         it means that there are currently one or more systems which desire 
         to receive multicast traffic for this source. If this timer expires 
         and the value of vRtrMldGrpIfHostGrpMode is 'include', the router 
         concludes that traffic from this particular source is no longer 
         desired on the attached network, and deletes this entry.
         This timer is treated differently when the value of vRtrMldGrpIfHostGrpMode
         is 'exclude'. If the value of vRtrMldGrpIfHostGrpSrcExpTime is non-zero 
         and router filter-mode for the group is 'exclude', it means that at 
         least one system desires to receive multicast traffic from this source.
         It should therefore be forwarded by a router on the network."
    ::= { vRtrMldGrpIfHostGrpSrcEntry 3 }

vRtrMldGrpIfHostGrpSrcType OBJECT-TYPE
    SYNTAX     TmnxMldGroupType
    MAX-ACCESS read-only
    STATUS     current
    DESCRIPTION
        "vRtrMldGrpIfHostGrpSrcType indicates how this source entry was learned. If 
         this source entry was learned by MLD, it will be set to 'dynamic'. 
         For statically configured sources, the value will be set to 'static'."
    ::= { vRtrMldGrpIfHostGrpSrcEntry 4 }

vRtrMldGrpIfHostGrpSrcMRDstVrId   OBJECT-TYPE
    SYNTAX       TmnxVRtrIDOrZero
    MAX-ACCESS   read-only
    STATUS       current
    DESCRIPTION  
        "The value of vRtrMldGrpIfHostGrpSrcMRDstVrId indicates the vRtrID of 
         the service where to redirect MLD multicast traffic to.
 
         The value zero means that no multicast redirection is configured."
    ::= { vRtrMldGrpIfHostGrpSrcEntry 5 }

vRtrMldGrpIfHostGrpSrcMRDstIfId  OBJECT-TYPE
    SYNTAX      InterfaceIndexOrZero
    MAX-ACCESS  read-only
    STATUS      current
    DESCRIPTION
        "The value of vRtrMldGrpIfHostGrpSrcMRDstIfId indicates the interface 
         index of the interface where to redirect MLD multicast traffic to.
 
         The value zero means that no multicast redirection is configured."
    ::= { vRtrMldGrpIfHostGrpSrcEntry 6 }

--
--  The MLD Source Group Host Database
--

vRtrMldGrpSrcHostTable OBJECT-TYPE
    SYNTAX     SEQUENCE OF VRtrMldGrpSrcHostEntry
    MAX-ACCESS not-accessible
    STATUS     current
    DESCRIPTION
        "The table listing the IP multicast sources corresponding to the 
         IP multicast groups per host. This table represents the host MLD 
         source, group database."
    ::= { vRtrMldHostObjs 6 }

vRtrMldGrpSrcHostEntry OBJECT-TYPE
    SYNTAX     VRtrMldGrpSrcHostEntry
    MAX-ACCESS not-accessible
    STATUS     current
    DESCRIPTION
        "An entry in the vRtrMldGrpSrcHostTable. 
         Each entry represents a source address from which receivers are
         interested/not interested in receiving multicast traffic. 
         "
    INDEX      { vRtrID, 
                 vRtrMldGrpSrcGroupAddrType,
                 vRtrMldGrpSrcGroupAddress, 
                 vRtrMldGrpSrcSourceAddrType,
                 vRtrMldGrpSrcSourceAddress, 
                 vRtrMldGrpSrcFwdOrBlk, 
                 vRtrMldHostAddressType,
                 vRtrMldHostAddress,
                 vRtrMldHostMacAddress,
                 vRtrMldHostPppoeSessionId }
    ::= { vRtrMldGrpSrcHostTable 1 }

VRtrMldGrpSrcHostEntry ::= SEQUENCE {
    vRtrMldGrpSrcHostUpTime         Unsigned32
}

vRtrMldGrpSrcHostUpTime    OBJECT-TYPE
    SYNTAX      Unsigned32
    UNITS       "seconds"
    MAX-ACCESS  read-only
    STATUS      current
    DESCRIPTION
        "vRtrMldGrpSrcHostUpTime indicates the time since this source group 
         entry got created."
    ::= { vRtrMldGrpSrcHostEntry 1 }

--
--  The MLD Host Source Group Table
--

vRtrMldHostGrpSrcTable OBJECT-TYPE
    SYNTAX     SEQUENCE OF VRtrMldHostGrpSrcEntry
    MAX-ACCESS not-accessible
    STATUS     current
    DESCRIPTION
        "The table listing the IP multicast sources
         corresponding to the IP multicast groups for which there 
         are members on a particular host. This table represents
         MLD host source, group database."
    ::= { vRtrMldHostObjs 7 }

vRtrMldHostGrpSrcEntry OBJECT-TYPE
    SYNTAX     VRtrMldHostGrpSrcEntry
    MAX-ACCESS not-accessible
    STATUS     current
    DESCRIPTION
        "An entry in the vRtrMldHostGrpSrcTable. 
         Each entry represents a source address from which receivers are
         interested/not interested in receiving multicast traffic from. 
         "
    INDEX      { vRtrID, 
                 vRtrMldHostAddressType,
                 vRtrMldHostAddress,
                 vRtrMldHostMacAddress,
                 vRtrMldHostPppoeSessionId, 
                 vRtrMldHostGroupAddressType,
                 vRtrMldHostGroupAddress, 
                 vRtrMldHostGrpSrcAddressType,
                 vRtrMldHostGrpSrcAddress }
    ::= { vRtrMldHostGrpSrcTable 1 }

VRtrMldHostGrpSrcEntry ::= SEQUENCE {
    vRtrMldHostGrpSrcExpiryTime     TimeInterval,
    vRtrMldHostGrpSrcType           TmnxMldGroupType,
    vRtrMldHostGrpSrcMcRdrDstVRtrID TmnxVRtrIDOrZero,
    vRtrMldHostGrpSrcMcRdrDstIfIdx  InterfaceIndexOrZero
}

vRtrMldHostGrpSrcExpiryTime OBJECT-TYPE
    SYNTAX     TimeInterval
    MAX-ACCESS read-only
    STATUS     current
    DESCRIPTION
        "The minimum amount of time remaining before this entry will
         be aged out.
         If the value of vRtrMldHostGrpSrcExpiryTime is non-zero and the 
         value of vRtrMldIfGroupMode corresponding to this entry is 'include',
         it means that there are currently one or more systems which desire 
         to receive multicast traffic for this source. If this timer expires 
         and the value of vRtrMldIfGroupMode is 'include', the router 
         concludes that traffic from this particular source is no longer 
         desired on the attached network, and deletes this entry.
         This timer is treated differently when the value of vRtrMldIfGroupMode
         is 'exclude'. If the value of vRtrMldHostGrpSrcExpiryTime is non-zero 
         and router filter-mode for the group is 'exclude', it means that at 
         least one system desires to receive multicast traffic from this source.
         It should therefore be forwarded by a router on the network."
    ::= { vRtrMldHostGrpSrcEntry 1 }

vRtrMldHostGrpSrcType OBJECT-TYPE
    SYNTAX     TmnxMldGroupType
    MAX-ACCESS read-only
    STATUS     current
    DESCRIPTION
        "vRtrMldHostGrpSrcType indicates how this source entry was learned. If 
         this source entry was learned by MLD, it will be set to 'dynamic'. 
         For statically configured sources, the value will be set to 'static'."
    ::= { vRtrMldHostGrpSrcEntry 2 }

vRtrMldHostGrpSrcMcRdrDstVRtrID   OBJECT-TYPE
    SYNTAX       TmnxVRtrIDOrZero
    MAX-ACCESS   read-only
    STATUS       current
    DESCRIPTION  
        "The value of vRtrMldHostGrpSrcMcRdrDstVRtrID indicates the vRtrID of
         the service where to redirect MLD multicast traffic to.
     
         The value zero means that no multicast redirection is configured."
    ::= { vRtrMldHostGrpSrcEntry 3 }

vRtrMldHostGrpSrcMcRdrDstIfIdx  OBJECT-TYPE
    SYNTAX      InterfaceIndexOrZero
    MAX-ACCESS  read-only
    STATUS      current
    DESCRIPTION
        "The value of vRtrMldHostGrpSrcMcRdrDstIfIdx indicates the interface 
         index of the interface where to redirect MLD multicast traffic to.
     
         The value zero means that no multicast redirection is configured."
    ::= { vRtrMldHostGrpSrcEntry 4 }


--
--  The MLD Host Group Table
--

vRtrMldHostGrpTable OBJECT-TYPE
    SYNTAX     SEQUENCE OF VRtrMldHostGrpEntry
    MAX-ACCESS not-accessible
    STATUS     current
    DESCRIPTION
        "The table listing the IP multicast groups for
         which there are members on a particular host. This table 
         represents the MLD group database."
    ::= { vRtrMldHostObjs 8 }

vRtrMldHostGrpEntry OBJECT-TYPE
    SYNTAX     VRtrMldHostGrpEntry
    MAX-ACCESS not-accessible
    STATUS     current
    DESCRIPTION
        "An entry in the vRtrMldHostGrpTable. Each entry represents a 
         group address for which receivers are
         interested/not interested in receiving multicast traffic."
    INDEX      { vRtrID, 
                 vRtrMldHostAddressType,
                 vRtrMldHostAddress,
                 vRtrMldHostMacAddress,
                 vRtrMldHostPppoeSessionId,
                 vRtrMldHostGroupAddressType,
                 vRtrMldHostGroupAddress }
    ::= { vRtrMldHostGrpTable 1 }

VRtrMldHostGrpEntry ::= SEQUENCE {
    vRtrMldHostGrpType              TmnxMldGroupType,
    vRtrMldHostGrpUpTime            TimeInterval,
    vRtrMldHostGrpExpiryTime        TimeInterval,
    vRtrMldHostGrpVer1HostTmr       TimeInterval,
    vRtrMldHostGrpMode              TmnxMldGroupFilterMode,
    vRtrMldHostGrpCompatMode        TmnxMldVersion,
    vRtrMldHostGrpMcRdrDstVrId      TmnxVRtrIDOrZero,
    vRtrMldHostGrpMcRdrDstIfId      InterfaceIndexOrZero
}

vRtrMldHostGrpType OBJECT-TYPE
    SYNTAX     TmnxMldGroupType
    MAX-ACCESS read-only
    STATUS     current
    DESCRIPTION
        "vRtrMldHostGrpType indicates how this group entry was learned. 
         If this group entry was learned by MLD, it will be set to 'dynamic'. 
         For statically configured groups, the value will be set to 'static'."
    ::= { vRtrMldHostGrpEntry 1 }

vRtrMldHostGrpUpTime OBJECT-TYPE
    SYNTAX     TimeInterval
    MAX-ACCESS read-only
    STATUS     current
    DESCRIPTION
        "The time elapsed since this entry was created."
    ::= { vRtrMldHostGrpEntry 2 }

vRtrMldHostGrpExpiryTime OBJECT-TYPE
    SYNTAX     TimeInterval
    MAX-ACCESS read-only
    STATUS     current
    DESCRIPTION
        "The value of vRtrMldHostGrpExpiryTime indicates the minimum amount 
         of time remaining before this entry will be aged out.

         If the value of vRtrMldHostGrpType is 'static', the value of 
         vRtrMldIfGroupExpiryTime will be set to maximum, which is 2147483647." 
    ::= { vRtrMldHostGrpEntry 3 }

vRtrMldHostGrpVer1HostTmr OBJECT-TYPE
    SYNTAX     TimeInterval
    MAX-ACCESS read-only
    STATUS     current
    DESCRIPTION
        "The time remaining until the local router will assume that
         there are no longer any MLD version 1 members on the IP
         subnet attached to this host.  Upon hearing any MLDv1
         Membership Report, this value is reset to the group
         membership timer.  While this time remaining is non-zero,
         the local router ignores any MLD Leave messages for this
         group that it receives on this host."
    ::= { vRtrMldHostGrpEntry 4 }

vRtrMldHostGrpMode OBJECT-TYPE
    SYNTAX     TmnxMldGroupFilterMode
    MAX-ACCESS read-only
    STATUS     current
    DESCRIPTION
        "vRtrMldHostGrpMode is based on the type of membership report(s) 
         received on the host for the group. In the 'include' mode, 
         reception of packets sent to the specified multicast address is 
         requested only from those IP source addresses listed in the 
         source-list parameter of the MLD membership report. 
         In 'exclude' mode, reception of packets sent to the given multicast 
         address is requested from all IP source addresses except those listed 
         in the source-list parameter.
         vRtrMldHostGrpSrcTable lists the sources corresponding to this group,
         if any."
    ::= { vRtrMldHostGrpEntry 5 }

vRtrMldHostGrpCompatMode OBJECT-TYPE
    SYNTAX     TmnxMldVersion
    MAX-ACCESS read-only
    STATUS     current
    DESCRIPTION
        "vRtrMldHostGrpCompatMode is used in order for routers to be 
         compatible with older version routers. MLDv2 hosts MUST operate 
         in version 1 and version 2 compatibility modes.  MLDv2 hosts MUST 
         keep state per local host regarding the compatibility mode of 
         each attached network.  A host's compatibility mode is determined 
         from the Host Compatibility Mode variable which can be in
         one of two states:  MLDv1 of MLDv2.  This variable is
         kept per interface and is dependent on the version of General Queries
         heard on that host as well as the Older Version Querier Present
         timers for the host."
    ::= { vRtrMldHostGrpEntry 6 }

vRtrMldHostGrpMcRdrDstVrId   OBJECT-TYPE
    SYNTAX       TmnxVRtrIDOrZero
    MAX-ACCESS   read-only
    STATUS       current
    DESCRIPTION  
        "The value of vRtrMldHostGrpMcRdrDstVrId indicates the vRtrID of 
         the service where to redirect MLD multicast traffic to.
 
         The value zero means that no multicast redirection is configured."
    ::= { vRtrMldHostGrpEntry 7 }

vRtrMldHostGrpMcRdrDstIfId  OBJECT-TYPE
    SYNTAX      InterfaceIndexOrZero
    MAX-ACCESS  read-only
    STATUS      current
    DESCRIPTION
        "The value of vRtrMldHostGrpMcRdrDstIfId indicates the interface 
         index of the interface where to redirect MLD multicast traffic to.
 
         The value zero means that no multicast redirection is configured."
    ::= { vRtrMldHostGrpEntry 8 }


--
--  The MLD Group Interface Host Table
--

vRtrMldGrpIfHostTable OBJECT-TYPE
    SYNTAX     SEQUENCE OF VRtrMldGrpIfHostEntry
    MAX-ACCESS not-accessible
    STATUS     current
    DESCRIPTION
        "The table listing the IP multicast groups for
         which there are members on a particular host. This table 
         represents the MLD group interface database."
    ::= { vRtrMldHostObjs 9 }

vRtrMldGrpIfHostEntry OBJECT-TYPE
    SYNTAX     VRtrMldGrpIfHostEntry
    MAX-ACCESS not-accessible
    STATUS     current
    DESCRIPTION
        "An entry in the vRtrMldGrpIfHostTable. Each entry represents a 
         host which is interested/not interested in receiving multicast traffic."
    INDEX      { vRtrID,
                 vRtrIfFwdSvcId,
                 vRtrGrpIfIndex,
                 vRtrMldHostAddressType,
                 vRtrMldHostAddress,
                 vRtrMldHostMacAddress,
                 vRtrMldHostPppoeSessionId }
    ::= { vRtrMldGrpIfHostTable 1 }

VRtrMldGrpIfHostEntry ::= SEQUENCE {
    vRtrMldGrpIfHostLastChangeTime  TimeStamp,
    vRtrMldGrpIfHostOperState       MldGrpItfOperState
}

vRtrMldGrpIfHostLastChangeTime OBJECT-TYPE
    SYNTAX      TimeStamp
    MAX-ACCESS  read-only
    STATUS      current
    DESCRIPTION
        "The sysUpTime when this row was last modified."
    ::= { vRtrMldGrpIfHostEntry 1 }

vRtrMldGrpIfHostOperState OBJECT-TYPE
    SYNTAX      MldGrpItfOperState
    MAX-ACCESS  read-only
    STATUS      current
    DESCRIPTION
        "The current operational state of MLD protocol for this host."
    ::= { vRtrMldGrpIfHostEntry 2 }
        
--
--  The MLD GrpIf SAP Table
--

vRtrMldGrpIfSapTable OBJECT-TYPE
    SYNTAX     SEQUENCE OF VRtrMldGrpIfSapEntry
    MAX-ACCESS not-accessible
    STATUS     current
    DESCRIPTION
        "The table listing the SAPs for which MLD protocol
         operation is active."
    ::= { vRtrMldGrpIfObjs 1 }

vRtrMldGrpIfSapEntry OBJECT-TYPE
    SYNTAX     VRtrMldGrpIfSapEntry
    MAX-ACCESS not-accessible
    STATUS     current
    DESCRIPTION
        "Each row entry in the vRtrMldGrpIfSapTable represents a SAP on
         this router that participates in the MLD protocol."
    INDEX      { vRtrID, 
                 vRtrIfFwdSvcId,
                 vRtrGrpIfIndex,
                 sapPortId,
                 sapEncapValue }
    ::= { vRtrMldGrpIfSapTable 1 }

VRtrMldGrpIfSapEntry ::= SEQUENCE {
    vRtrMldGrpIfSapLastChangeTime    TimeStamp,
    vRtrMldGrpIfSapOperState         MldGrpItfOperState,
    vRtrMldGrpIfSapAdminVersion      TmnxMldVersion,
    vRtrMldGrpIfSapOperVersion       TmnxMldVersion,
    vRtrMldGrpIfSapGroupCount        Unsigned32,
    vRtrMldGrpIfSapNextGenQueryTime  Unsigned32,
    vRtrMldGrpIfSapMaxGroups         Unsigned32,
    vRtrMldGrpIfSapMaxGroupsTillNow  Counter32,
    vRtrMldGrpIfSapMaxSources        Unsigned32,
    vRtrMldGrpIfSapMaxGrpSources     Unsigned32,
    vRtrMldGrpIfSapQryInterval       Unsigned32,
    vRtrMldGrpIfSapLastLstnrQryIntvl Unsigned32,
    vRtrMldGrpIfSapQryResponseIntvl  Unsigned32
}

vRtrMldGrpIfSapLastChangeTime       OBJECT-TYPE
    SYNTAX      TimeStamp
    MAX-ACCESS  read-only
    STATUS      current
    DESCRIPTION
        "The sysUpTime when this row was last modified."
    ::= { vRtrMldGrpIfSapEntry 1 }

vRtrMldGrpIfSapOperState        OBJECT-TYPE
    SYNTAX      MldGrpItfOperState
    MAX-ACCESS  read-only
    STATUS      current
    DESCRIPTION
        "The current operational state of MLD protocol for this SAP."
    ::= { vRtrMldGrpIfSapEntry 2 }

vRtrMldGrpIfSapAdminVersion OBJECT-TYPE
    SYNTAX     TmnxMldVersion
    MAX-ACCESS read-only
    STATUS     current
    DESCRIPTION
        "The configured version of MLD which is running for this SAP.
         
         For MLD to function correctly, all routers on a LAN must be configured
         to run the same version of MLD on that LAN."
    DEFVAL { version2 }
    ::= { vRtrMldGrpIfSapEntry 3 }

vRtrMldGrpIfSapOperVersion OBJECT-TYPE
    SYNTAX     TmnxMldVersion
    MAX-ACCESS read-only
    STATUS     current
    DESCRIPTION
        "The operational version of MLD which is running for this SAP."
    ::= { vRtrMldGrpIfSapEntry 4 }

vRtrMldGrpIfSapGroupCount OBJECT-TYPE
    SYNTAX     Unsigned32
    MAX-ACCESS read-only
    STATUS     current
    DESCRIPTION
        "vRtrMldGrpIfSapGroupCount is the number of multicast groups which have
         been learned by the router for this SAP."
    ::= { vRtrMldGrpIfSapEntry 5 }

vRtrMldGrpIfSapNextGenQueryTime OBJECT-TYPE
    SYNTAX     Unsigned32
    UNITS      "seconds"
    MAX-ACCESS read-only
    STATUS     current
    DESCRIPTION
        "If this router is the querier (vRtrMldIfQuerier is a 
         local address), vRtrMldGrpIfSapNextGenQueryTime is the 
         time remaining before the general query is sent for this SAP.
         
         If this router is not the querier for the SAP, the value
         of this object will be zero."
    ::= { vRtrMldGrpIfSapEntry 6 }

vRtrMldGrpIfSapMaxGroups OBJECT-TYPE
    SYNTAX     Unsigned32 (0|1..16000)
    MAX-ACCESS read-only
    STATUS     current
    DESCRIPTION
        "The value of vRtrMldGrpIfSapMaxGroups specifies the maximum number of
         groups for which MLD can have local receiver information based on
         received MLD reports on this SAP. 
         
         When this configuration is changed dynamically to a value lower than
         currently accepted number of groups, the groups that are already
         accepted are not deleted.
         
         Only new groups will not be allowed. When this object has a value of 0,
         there is no limit to the number of groups."
    DEFVAL { 0 }
    ::= { vRtrMldGrpIfSapEntry 7 }

vRtrMldGrpIfSapMaxGroupsTillNow OBJECT-TYPE
    SYNTAX     Counter32
    MAX-ACCESS read-only
    STATUS     current
    DESCRIPTION
        "The value of vRtrMldGrpIfSapMaxGroupsTillNow indicates the highest 
         value that vRtrMldGrpIfSapMaxGroups had till now."
    ::= { vRtrMldGrpIfSapEntry 8 }

vRtrMldGrpIfSapMaxSources OBJECT-TYPE
    SYNTAX     Unsigned32 (0|1..1000)
    MAX-ACCESS read-only
    STATUS     current
    DESCRIPTION
        "The value of vRtrMldGrpIfSapMaxSources specifies the maximum number of
         sources per group for which MLD can have local receiver information 
         based on received MLD reports on this SAP. 
         
         When this configuration is changed dynamically to a value lower than
         currently accepted number of sources, the sources that are already
         accepted are not deleted.
         
         Only new sources will not be allowed. When this object has a value of 0,
         there is no limit to the number of sources."
    DEFVAL { 0 }
    ::= { vRtrMldGrpIfSapEntry 9 }

vRtrMldGrpIfSapMaxGrpSources OBJECT-TYPE
    SYNTAX     Unsigned32 (0|1..32000)
    MAX-ACCESS read-only
    STATUS     current
    DESCRIPTION
        "The value of vRtrMldGrpIfSapMaxGrpSources specifies the maximum number 
         of group sources per group for which MLD can have local receiver 
         information based on received MLD reports on this SAP. 
         
         When this configuration is changed dynamically to a value lower than
         currently accepted number of sources, the sources that are already
         accepted are not deleted.
         
         Only new sources will not be allowed. When this object has a value of 0,
         there is no limit to the number of sources."
    DEFVAL { 0 }
    ::= { vRtrMldGrpIfSapEntry 10 }

vRtrMldGrpIfSapQryInterval OBJECT-TYPE
    SYNTAX     Unsigned32 (0|2..1024)
    UNITS      "seconds"
    MAX-ACCESS read-only
    STATUS     current
    DESCRIPTION
        "The value of vRtrMldGrpIfSapQryInterval indicates the frequency at 
         which the MLD Host-Query packets are transmitted on this SAP."
    ::= { vRtrMldGrpIfSapEntry 11 }

vRtrMldGrpIfSapLastLstnrQryIntvl OBJECT-TYPE
    SYNTAX     Unsigned32 (0|1..1023)
    UNITS      "seconds"
    MAX-ACCESS read-only
    STATUS     current
    DESCRIPTION
        "The value of vRtrMldGrpIfSapLastLstnrQryIntvl indicates the Max  
         Response Time inserted into Group-Specific Queries sent in response 
         to Leave Group messages, and is also the amount of time between
         Group-Specific Query messages.  This value may be tuned to modify the
         leave latency of the network.  A reduced value results in reduced 
         time to detect the loss of the last member of a group."
    ::= { vRtrMldGrpIfSapEntry 12 }

vRtrMldGrpIfSapQryResponseIntvl OBJECT-TYPE
    SYNTAX     Unsigned32 (0|1..1023)
    UNITS      "seconds"
    MAX-ACCESS read-only
    STATUS     current
    DESCRIPTION
        "The value of vRtrMldGrpIfSapQryResponseIntvl indicates the maximum 
         query response time advertised in MLD v2 queries on this SAP."
    ::= { vRtrMldGrpIfSapEntry 13 }

--
--  The MLD GrpIf SAP Statistics Table
--

vRtrMldGrpIfSapStatsTable OBJECT-TYPE
    SYNTAX     SEQUENCE OF VRtrMldGrpIfSapStatsEntry
    MAX-ACCESS not-accessible
    STATUS     current
    DESCRIPTION
        "The table listing the MLD statistics for
         a particular SAP on a group-interface."
    ::= { vRtrMldGrpIfObjs 2 }

vRtrMldGrpIfSapStatsEntry OBJECT-TYPE
    SYNTAX     VRtrMldGrpIfSapStatsEntry
    MAX-ACCESS not-accessible
    STATUS     current
    DESCRIPTION
        "An entry in the vRtrMldGrpIfSapStatsTable."
    INDEX      { vRtrID, 
                 vRtrIfFwdSvcId,
                 vRtrGrpIfIndex,
                 sapPortId,
                 sapEncapValue }
    ::= { vRtrMldGrpIfSapStatsTable 1 }

VRtrMldGrpIfSapStatsEntry ::= SEQUENCE {
    vRtrMldGrpIfSapTxGenQueries     Counter32,
    vRtrMldGrpIfSapTxGrpQueries     Counter32,
    vRtrMldGrpIfSapTxGrpSrcQueries  Counter32,
    vRtrMldGrpIfSapTxV1Reports      Counter32,
    vRtrMldGrpIfSapTxV2Reports      Counter32,
    vRtrMldGrpIfSapTxLeaves         Counter32,
    vRtrMldGrpIfSapTxErrors         Counter32,
    vRtrMldGrpIfSapRxGenQueries     Counter32,
    vRtrMldGrpIfSapRxGrpQueries     Counter32,
    vRtrMldGrpIfSapRxGrpSrcQueries  Counter32,
    vRtrMldGrpIfSapRxV1Reports      Counter32,
    vRtrMldGrpIfSapRxV2Reports      Counter32,
    vRtrMldGrpIfSapRxLeaves         Counter32,
    vRtrMldGrpIfSapRxBadLenPkts     Counter32,
    vRtrMldGrpIfSapRxBadChksumPkts  Counter32,
    vRtrMldGrpIfSapRxUnknTypePkts   Counter32,
    vRtrMldGrpIfSapRxBadRecvIfPkts  Counter32,
    vRtrMldGrpIfSapRxNonLocal       Counter32,
    vRtrMldGrpIfSapRxWrongVersions  Counter32,
    vRtrMldGrpIfSapImportPlcyDrops  Counter32,
    vRtrMldGrpIfSapRxNoRtrAlertPkts Counter32,
    vRtrMldGrpIfSapRxBadEncodings   Counter32,
    vRtrMldGrpIfSapRxPktDrops       Counter32,
    vRtrMldGrpIfSapStatsStarGTypes  Gauge32,
    vRtrMldGrpIfSapStatsSGTypes     Gauge32,
    vRtrMldGrpIfSapStatsMcacPlcyDrp Counter32,
    vRtrMldGrpIfSapRxLocalScopePkts Counter32,
    vRtrMldGrpIfSapRxRsvdScopePkts  Counter32
}

vRtrMldGrpIfSapTxGenQueries OBJECT-TYPE
    SYNTAX       Counter32
    MAX-ACCESS   read-only
    STATUS       current
    DESCRIPTION
        "The value of vRtrMldGrpIfSapTxGenQueries indicates the number of MLD 
         General Queries transmitted for this SAP."
    ::= { vRtrMldGrpIfSapStatsEntry 1 }

vRtrMldGrpIfSapTxGrpQueries OBJECT-TYPE
    SYNTAX       Counter32
    MAX-ACCESS   read-only
    STATUS       current
    DESCRIPTION
        "The value of vRtrMldGrpIfSapTxGrpQueries indicates the number of MLD 
         Group Specific Queries transmitted for this SAP."
    ::= { vRtrMldGrpIfSapStatsEntry 2 }

vRtrMldGrpIfSapTxGrpSrcQueries OBJECT-TYPE
    SYNTAX       Counter32
    MAX-ACCESS   read-only
    STATUS       current
    DESCRIPTION
        "The value of vRtrMldGrpIfSapTxGrpSrcQueries indicates the number of MLD 
         Group and Source Specific Queries transmitted for this SAP."
    ::= { vRtrMldGrpIfSapStatsEntry 3 }

vRtrMldGrpIfSapTxV1Reports OBJECT-TYPE
    SYNTAX       Counter32
    MAX-ACCESS   read-only
    STATUS       current
    DESCRIPTION
        "The value of vRtrMldGrpIfSapTxV1Reports indicates the total number of 
         MLD V1 Reports transmitted for this SAP."
    ::= { vRtrMldGrpIfSapStatsEntry 4 }

vRtrMldGrpIfSapTxV2Reports OBJECT-TYPE
    SYNTAX       Counter32
    MAX-ACCESS   read-only
    STATUS       current
    DESCRIPTION
        "The value of vRtrMldGrpIfSapTxV2Reports indicates the total number of 
         MLD V2 Reports transmitted for this SAP."
    ::= { vRtrMldGrpIfSapStatsEntry 5 }

vRtrMldGrpIfSapTxLeaves OBJECT-TYPE
    SYNTAX       Counter32
    MAX-ACCESS   read-only
    STATUS       current
    DESCRIPTION
        "The value of vRtrMldGrpIfSapTxLeaves indicates the total number of MLD
         Leaves transmitted for this SAP."
    ::= { vRtrMldGrpIfSapStatsEntry 6 }

vRtrMldGrpIfSapTxErrors OBJECT-TYPE
    SYNTAX       Counter32
    MAX-ACCESS   read-only
    STATUS       current
    DESCRIPTION
        "The value of vRtrMldGrpIfSapTxErrors indicates the total number of times
         there was an error transmitting MLD packets for this SAP."
    ::= { vRtrMldGrpIfSapStatsEntry 7 }

vRtrMldGrpIfSapRxGenQueries OBJECT-TYPE
    SYNTAX       Counter32
    MAX-ACCESS   read-only
    STATUS       current
    DESCRIPTION
        "The value of vRtrMldGrpIfSapRxGenQueries indicates the total number of MLD 
         General Queries received for this SAP."
    ::= { vRtrMldGrpIfSapStatsEntry 8 }

vRtrMldGrpIfSapRxGrpQueries OBJECT-TYPE
    SYNTAX       Counter32
    MAX-ACCESS   read-only
    STATUS       current
    DESCRIPTION
        "The value of vRtrMldGrpIfSapRxGrpQueries indicates the number of MLD 
         Group Specific Queries received for this SAP."
    ::= { vRtrMldGrpIfSapStatsEntry 9 }

vRtrMldGrpIfSapRxGrpSrcQueries OBJECT-TYPE
    SYNTAX       Counter32
    MAX-ACCESS   read-only
    STATUS       current
    DESCRIPTION
        "The value of vRtrMldGrpIfSapRxGrpSrcQueries indicates the number of MLD 
         Group and Source Specific Queries received for this SAP."
    ::= { vRtrMldGrpIfSapStatsEntry 10 }

vRtrMldGrpIfSapRxV1Reports OBJECT-TYPE
    SYNTAX       Counter32
    MAX-ACCESS   read-only
    STATUS       current
    DESCRIPTION
        "The value of vRtrMldGrpIfSapRxV1Reports indicates the total number of 
         MLD V1 Reports received for this SAP."
    ::= { vRtrMldGrpIfSapStatsEntry 11 }

vRtrMldGrpIfSapRxV2Reports OBJECT-TYPE
    SYNTAX       Counter32
    MAX-ACCESS   read-only
    STATUS       current
    DESCRIPTION
        "The value of vRtrMldGrpIfSapRxV2Reports indicates the total number of 
         MLD V2 Reports received for this SAP."
    ::= { vRtrMldGrpIfSapStatsEntry 12 }

vRtrMldGrpIfSapRxLeaves OBJECT-TYPE
    SYNTAX       Counter32
    MAX-ACCESS   read-only
    STATUS       current
    DESCRIPTION
        "The value of vRtrMldGrpIfSapRxLeaves indicates the total number of 
         MLD Leaves received for this SAP."
    ::= { vRtrMldGrpIfSapStatsEntry 13 }

vRtrMldGrpIfSapRxBadLenPkts OBJECT-TYPE
    SYNTAX       Counter32
    MAX-ACCESS   read-only
    STATUS       current
    DESCRIPTION
        "The value of vRtrMldGrpIfSapRxBadLenPkts indicates the total number of 
         MLD packets with bad length received for this SAP."
    ::= { vRtrMldGrpIfSapStatsEntry 14 }

vRtrMldGrpIfSapRxBadChksumPkts OBJECT-TYPE
    SYNTAX       Counter32
    MAX-ACCESS   read-only
    STATUS       current
    DESCRIPTION
        "The value of vRtrMldGrpIfSapRxBadChksumPkts indicates the total number of 
         MLD packets with bad checksum received for this SAP."
    ::= { vRtrMldGrpIfSapStatsEntry 15 }

vRtrMldGrpIfSapRxUnknTypePkts OBJECT-TYPE
    SYNTAX       Counter32
    MAX-ACCESS   read-only
    STATUS       current
    DESCRIPTION
        "The value of vRtrMldGrpIfSapRxUnknTypePkts indicates the total number of 
         MLD packets with unknown type received for this SAP."
    ::= { vRtrMldGrpIfSapStatsEntry 16 }

vRtrMldGrpIfSapRxBadRecvIfPkts OBJECT-TYPE
    SYNTAX       Counter32
    MAX-ACCESS   read-only
    STATUS       current
    DESCRIPTION
        "The value of vRtrMldGrpIfSapRxBadRecvIfPkts indicates the total 
         number of MLD packets incorrectly received for this SAP."
    ::= { vRtrMldGrpIfSapStatsEntry 17 }

vRtrMldGrpIfSapRxNonLocal OBJECT-TYPE
    SYNTAX       Counter32
    MAX-ACCESS   read-only
    STATUS       current
    DESCRIPTION
        "The value of vRtrMldGrpIfSapRxNonLocal indicates the total number of 
        MLD packets received from a non-local sender."
    ::= { vRtrMldGrpIfSapStatsEntry 18 }

vRtrMldGrpIfSapRxWrongVersions OBJECT-TYPE
    SYNTAX       Counter32
    MAX-ACCESS   read-only
    STATUS       current
    DESCRIPTION
        "The value of vRtrMldGrpIfSapRxWrongVersions indicates the total number
         of MLD packets with wrong versions received for this SAP."
    ::= { vRtrMldGrpIfSapStatsEntry 19 }

vRtrMldGrpIfSapImportPlcyDrops OBJECT-TYPE
    SYNTAX       Counter32
    MAX-ACCESS   read-only
    STATUS       current
    DESCRIPTION
        "The value of vRtrMldGrpIfSapImportPlcyDrops indicates the total number 
         of times MLD protocol instance matched the host IP address or 
         group/source addresses specified in the import policy."
    ::= { vRtrMldGrpIfSapStatsEntry 20 }

vRtrMldGrpIfSapRxNoRtrAlertPkts OBJECT-TYPE
    SYNTAX       Counter32
    MAX-ACCESS   read-only
    STATUS       current
    DESCRIPTION
        "The value of vRtrMldGrpIfSapRxNoRtrAlertPkts indicates the total number  
         of MLDv2 packets received for this SAP which did not have the 
         router alert flag set."
    ::= { vRtrMldGrpIfSapStatsEntry 21 }

vRtrMldGrpIfSapRxBadEncodings OBJECT-TYPE
    SYNTAX       Counter32
    MAX-ACCESS   read-only
    STATUS       current
    DESCRIPTION
        "The value of vRtrMldGrpIfSapRxBadEncodings indicates the total number 
         of MLD packets received for this SAP which were not encoded
         correctly."
    ::= { vRtrMldGrpIfSapStatsEntry 22 }

vRtrMldGrpIfSapRxPktDrops OBJECT-TYPE
    SYNTAX       Counter32
    MAX-ACCESS   read-only
    STATUS       current
    DESCRIPTION
        "The value of vRtrMldGrpIfSapRxPktDrops indicates the total number of 
         MLD packets that were received for this SAP but were dropped."
    ::= { vRtrMldGrpIfSapStatsEntry 23 }

vRtrMldGrpIfSapStatsStarGTypes OBJECT-TYPE
    SYNTAX       Gauge32
    MAX-ACCESS   read-only
    STATUS       current
    DESCRIPTION
        "vRtrMldGrpIfSapStatsStarGTypes indicates the number of entries for this 
         SAP for which the source type is 'starG'."
    ::= { vRtrMldGrpIfSapStatsEntry 24 }

vRtrMldGrpIfSapStatsSGTypes OBJECT-TYPE
    SYNTAX       Gauge32
    MAX-ACCESS   read-only
    STATUS       current
    DESCRIPTION
        "The value of vRtrMldGrpIfSapStatsSGTypes indicates the number of entries 
         for this SAP for which the source type is 'sg'."
    ::= { vRtrMldGrpIfSapStatsEntry 25 }

vRtrMldGrpIfSapStatsMcacPlcyDrp OBJECT-TYPE
    SYNTAX       Counter32
    MAX-ACCESS   read-only
    STATUS       current
    DESCRIPTION
        "The value of the object vRtrMldGrpIfSapStatsMcacPlcyDrp indicates 
         the number times an MLD Group is dropped because of applying a
         multicast CAC policy for this SAP."
    ::= { vRtrMldGrpIfSapStatsEntry 26 }

vRtrMldGrpIfSapRxLocalScopePkts OBJECT-TYPE
    SYNTAX       Counter32
    MAX-ACCESS   read-only
    STATUS       current
    DESCRIPTION
        "The value of the object vRtrMldGrpIfSapRxLocalScopePkts indicates 
         the number of MLD packets received on the link-local scope IPv4 
         multicast address."
    ::= { vRtrMldGrpIfSapStatsEntry 27 }

vRtrMldGrpIfSapRxRsvdScopePkts OBJECT-TYPE
    SYNTAX       Counter32
    MAX-ACCESS   read-only
    STATUS       current
    DESCRIPTION
        "The value of the object vRtrMldGrpIfSapRxRsvdScopePkts indicates 
         the number of MLD packets received on the reserved scope IPv4
         multicast address."
    ::= { vRtrMldGrpIfSapStatsEntry 28 }


--
--  The MLD Group Interface SAP Group Table
--

vRtrMldGrpIfSapGrpTable OBJECT-TYPE
    SYNTAX     SEQUENCE OF VRtrMldGrpIfSapGrpEntry
    MAX-ACCESS not-accessible
    STATUS     current
    DESCRIPTION
        "The table listing the IP multicast groups for
         which there are members on a particular SAP. This table 
         represents the MLD group database."
    ::= { vRtrMldGrpIfObjs 3 }

vRtrMldGrpIfSapGrpEntry OBJECT-TYPE
    SYNTAX     VRtrMldGrpIfSapGrpEntry
    MAX-ACCESS not-accessible
    STATUS     current
    DESCRIPTION
        "An entry in the vRtrMldGrpIfSapGrpTable. Each entry represents a 
         group address for which receivers are
         interested/not interested in receiving multicast traffic."
    INDEX      { vRtrID, 
                 vRtrIfFwdSvcId,
                 vRtrGrpIfIndex,
                 sapPortId,
                 sapEncapValue,
                 vRtrMldGrpIfSapGroupAddressType,
                 vRtrMldGrpIfSapGroupAddress }
    ::= { vRtrMldGrpIfSapGrpTable 1 }

VRtrMldGrpIfSapGrpEntry ::= SEQUENCE {
    vRtrMldGrpIfSapGroupAddressType  InetAddressType,
    vRtrMldGrpIfSapGroupAddress      InetAddress,
    vRtrMldGrpIfSapGrpType           TmnxMldGroupType,
    vRtrMldGrpIfSapGrpUpTime         TimeInterval,
    vRtrMldGrpIfSapGrpExpiryTime     TimeInterval,
    vRtrMldGrpIfSapGrpVer1HostTmr    TimeInterval,
    vRtrMldGrpIfSapGrpMode           TmnxMldGroupFilterMode,
    vRtrMldGrpIfSapGrpCompatMode     TmnxMldVersion
}

vRtrMldGrpIfSapGroupAddressType OBJECT-TYPE
    SYNTAX     InetAddressType
    MAX-ACCESS not-accessible
    STATUS     current
    DESCRIPTION
        "The value of vRtrMldGrpIfSapGroupAddressType indicates the type of 
         address to be used for vRtrMldGrpIfSapGroupAddress."         
    ::= { vRtrMldGrpIfSapGrpEntry 1 }

vRtrMldGrpIfSapGroupAddress OBJECT-TYPE
    SYNTAX     InetAddress (SIZE(16))
    MAX-ACCESS not-accessible
    STATUS     current
    DESCRIPTION
        "The IP multicast group address for which this entry
         contains information."
    ::= { vRtrMldGrpIfSapGrpEntry 2 }

vRtrMldGrpIfSapGrpType OBJECT-TYPE
    SYNTAX     TmnxMldGroupType
    MAX-ACCESS read-only
    STATUS     current
    DESCRIPTION
        "vRtrMldGrpIfSapGrpType indicates how this group entry was learned. 
         If this group entry was learned by MLD, it will be set to 'dynamic'. 
         For statically configured groups, the value will be set to 'static'."
    ::= { vRtrMldGrpIfSapGrpEntry 3 }

vRtrMldGrpIfSapGrpUpTime OBJECT-TYPE
    SYNTAX     TimeInterval
    MAX-ACCESS read-only
    STATUS     current
    DESCRIPTION
        "The time elapsed since this entry was created."
    ::= { vRtrMldGrpIfSapGrpEntry 4 }

vRtrMldGrpIfSapGrpExpiryTime OBJECT-TYPE
    SYNTAX     TimeInterval
    MAX-ACCESS read-only
    STATUS     current
    DESCRIPTION
        "The value of vRtrMldGrpIfSapGrpExpiryTime indicates the minimum amount 
         of time remaining before this entry will be aged out.

         If the value of vRtrMldGrpIfSapGrpType is 'static', the value of 
         vRtrMldGrpIfHostGrpExpiryTime will be set to maximum,
         which is 2147483647." 
    ::= { vRtrMldGrpIfSapGrpEntry 5 }

vRtrMldGrpIfSapGrpVer1HostTmr OBJECT-TYPE
    SYNTAX     TimeInterval
    MAX-ACCESS read-only
    STATUS     current
    DESCRIPTION
        "The time remaining until the local router will assume that
         there are no longer any MLD version 1 members on the IP
         subnet attached to this SAP.  Upon hearing any MLDv1
         Membership Report, this value is reset to the group
         membership timer.  While this time remaining is non-zero,
         the local router ignores any MLD Leave messages for this
         group that it receives on this SAP."
    ::= { vRtrMldGrpIfSapGrpEntry 6 }

vRtrMldGrpIfSapGrpMode OBJECT-TYPE
    SYNTAX     TmnxMldGroupFilterMode
    MAX-ACCESS read-only
    STATUS     current
    DESCRIPTION
        "vRtrMldGrpIfHostGrpMode is based on the type of membership report(s) 
         received on the SAP for the group. In the 'include' mode, 
         reception of packets sent to the specified multicast address is 
         requested only from those IP source addresses listed in the 
         source-list parameter of the MLD membership report.
         
         In 'exclude' mode, reception of packets sent to the given multicast 
         address is requested from all IP source addresses except those listed 
         in the source-list parameter.
         
         vRtrMldGrpIfSapGrpSrcTable lists the sources corresponding to this group,
         if any."
    ::= { vRtrMldGrpIfSapGrpEntry 7 }

vRtrMldGrpIfSapGrpCompatMode OBJECT-TYPE
    SYNTAX     TmnxMldVersion
    MAX-ACCESS read-only
    STATUS     current
    DESCRIPTION
        "vRtrMldGrpIfSapGrpCompatMode is used in order for routers to be 
         compatible with older version routers. MLDv2 hosts MUST operate 
         in version 1 and version 2 compatibility modes.  MLDv2 SAPs MUST 
         keep state per local SAP regarding the compatibility mode of 
         each attached network.  A SAPs compatibility mode is determined 
         from the Host Compatibility Mode variable which can be in
         one of three states:  MLDv1 or MLDv2.  This variable is
         kept per interface and is dependent on the version of General Queries
         heard on that SAP as well as the Older Version Querier Present
         timers for the SAP."
    ::= { vRtrMldGrpIfSapGrpEntry 8 }

--
--  The MLD Group Interface SAP Group Source Table
--

vRtrMldGrpIfSapGrpSrcTable OBJECT-TYPE
    SYNTAX     SEQUENCE OF VRtrMldGrpIfSapGrpSrcEntry
    MAX-ACCESS not-accessible
    STATUS     current
    DESCRIPTION
        "The table listing the IP multicast sources
         corresponding to the IP multicast groups for which there 
         are members on a particular SAP. This table represents
         MLD source, group database."
    ::= { vRtrMldGrpIfObjs 4 }

vRtrMldGrpIfSapGrpSrcEntry OBJECT-TYPE
    SYNTAX     VRtrMldGrpIfSapGrpSrcEntry
    MAX-ACCESS not-accessible
    STATUS     current
    DESCRIPTION
        "An entry in the vRtrMldGrpIfSapGrpSrcTable. 
         Each entry represents a source address from which receivers are
         interested/not interested in receiving multicast traffic from."
    INDEX      { vRtrID,
                 vRtrIfFwdSvcId,
                 vRtrGrpIfIndex,
                 sapPortId,
                 sapEncapValue,
                 vRtrMldGrpIfSapGroupAddressType,
                 vRtrMldGrpIfSapGroupAddress, 
                 vRtrMldGrpIfSapGrpSrcAddressType,
                 vRtrMldGrpIfSapGrpSrcAddress }
    ::= { vRtrMldGrpIfSapGrpSrcTable 1 }

VRtrMldGrpIfSapGrpSrcEntry ::= SEQUENCE {
    vRtrMldGrpIfSapGrpSrcAddressType InetAddressType,
    vRtrMldGrpIfSapGrpSrcAddress     InetAddress,
    vRtrMldGrpIfSapGrpSrcExpTime     TimeInterval,
    vRtrMldGrpIfSapGrpSrcType        TmnxMldGroupType
}

vRtrMldGrpIfSapGrpSrcAddressType OBJECT-TYPE
    SYNTAX     InetAddressType
    MAX-ACCESS not-accessible
    STATUS     current
    DESCRIPTION
        "The value of vRtrMldGrpIfSapGrpSrcAddressType indicates the type of 
         address to be used for vRtrMldGrpIfSapGrpSrcAddress."         
    ::= { vRtrMldGrpIfSapGrpSrcEntry 1 }

vRtrMldGrpIfSapGrpSrcAddress OBJECT-TYPE
    SYNTAX     InetAddress (SIZE(16))
    MAX-ACCESS not-accessible
    STATUS     current
    DESCRIPTION
        "The address of the source sending multicast traffic to the group
         identified by vRtrMldGrpIfSapGroupAddress."
    ::= { vRtrMldGrpIfSapGrpSrcEntry 2 }

vRtrMldGrpIfSapGrpSrcExpTime OBJECT-TYPE
    SYNTAX     TimeInterval
    MAX-ACCESS read-only
    STATUS     current
    DESCRIPTION
        "The minimum amount of time remaining before this entry will be aged out.
         If the value of vRtrMldGrpIfSapGrpSrcExpTime is non-zero and the 
         value of vRtrMldGrpIfSapGrpMode corresponding to this entry is 'include',
         it means that there are currently one or more systems which desire 
         to receive multicast traffic for this source. If this timer expires 
         and the value of vRtrMldGrpIfHostGrpMode is 'include', the router 
         concludes that traffic from this particular source is no longer 
         desired on the attached network, and deletes this entry.
         
         This timer is treated differently when the value of vRtrMldGrpIfSapGrpMode
         is 'exclude'. If the value of vRtrMldGrpIfSapGrpSrcExpTime is non-zero 
         and router filter-mode for the group is 'exclude', it means that at 
         least one system desires to receive multicast traffic from this source.
         It should therefore be forwarded by a router on the network."
    ::= { vRtrMldGrpIfSapGrpSrcEntry 3 }

vRtrMldGrpIfSapGrpSrcType OBJECT-TYPE
    SYNTAX     TmnxMldGroupType
    MAX-ACCESS read-only
    STATUS     current
    DESCRIPTION
        "vRtrMldGrpIfSapGrpSrcType indicates how this source entry was learned. If 
         this source entry was learned by MLD, it will be set to 'dynamic'. 
         For statically configured sources, the value will be set to 'static'."
    ::= { vRtrMldGrpIfSapGrpSrcEntry 4 }

--
--  The MLD Source Group Group Interface SAP Database
--

vRtrMldGrpSrcGrpIfSapTable OBJECT-TYPE
    SYNTAX     SEQUENCE OF VRtrMldGrpSrcGrpIfSapEntry
    MAX-ACCESS not-accessible
    STATUS     current
    DESCRIPTION
        "The table listing the IP multicast sources corresponding to the 
         IP multicast groups per SAP. This table represents the host MLD 
         source, group database."
    ::= { vRtrMldGrpIfObjs 5 }

vRtrMldGrpSrcGrpIfSapEntry OBJECT-TYPE
    SYNTAX     VRtrMldGrpSrcGrpIfSapEntry
    MAX-ACCESS not-accessible
    STATUS     current
    DESCRIPTION
        "An entry in the vRtrMldGrpSrcGrpIfSapTable. 
         Each entry represents a source address from which receivers are
         interested/not interested in receiving multicast traffic. 
         "
    INDEX      { vRtrID, 
                 vRtrMldGrpSrcGroupAddrType,
                 vRtrMldGrpSrcGroupAddress,
                 vRtrMldGrpSrcSourceAddrType,
                 vRtrMldGrpSrcSourceAddress, 
                 vRtrMldGrpSrcFwdOrBlk, 
                 vRtrIfFwdSvcId,
                 vRtrGrpIfIndex,
                 sapPortId,
                 sapEncapValue }
    ::= { vRtrMldGrpSrcGrpIfSapTable 1 }

VRtrMldGrpSrcGrpIfSapEntry ::= SEQUENCE {
    vRtrMldGrpSrcGrpIfSapUpTime     Unsigned32
}

vRtrMldGrpSrcGrpIfSapUpTime    OBJECT-TYPE
    SYNTAX      Unsigned32
    UNITS       "seconds"
    MAX-ACCESS  read-only
    STATUS      current
    DESCRIPTION
        "vRtrMldGrpSrcGrpIfSapUpTime indicates the time since this source group 
         entry got created."
    ::= { vRtrMldGrpSrcGrpIfSapEntry 1 }

--
-- The MLD Group Source Summary Table
--

vRtrMldGrpSrcSummaryTable OBJECT-TYPE
    SYNTAX     SEQUENCE OF VRtrMldGrpSrcSummaryEntry
    MAX-ACCESS not-accessible
    STATUS     current
    DESCRIPTION
        "The table listing the IP multicast Group/Source summary counters."
    ::= { vRtrMldProtocolObjs 7 }

vRtrMldGrpSrcSummaryEntry OBJECT-TYPE
    SYNTAX     VRtrMldGrpSrcSummaryEntry
    MAX-ACCESS not-accessible
    STATUS     current
    DESCRIPTION
        "An entry in the vRtrMldGrpSrcSummaryTable.
         
         Each entry represents the summary counters for each Group/Source
         combination."
    INDEX      { vRtrID, 
                 vRtrMldGrpSrcGroupAddrType,
                 vRtrMldGrpSrcGroupAddress, 
                 vRtrMldGrpSrcSourceAddrType,
                 vRtrMldGrpSrcSourceAddress }
    ::= { vRtrMldGrpSrcSummaryTable 1 }

VRtrMldGrpSrcSummaryEntry ::= SEQUENCE {
    vRtrMldGrpSrcSummFwdInterfaces   Gauge32,
    vRtrMldGrpSrcSummBlkInterfaces   Gauge32,
    vRtrMldGrpSrcSummFwdHosts        Gauge32,
    vRtrMldGrpSrcSummBlkHosts        Gauge32,
    vRtrMldGrpSrcSummFwdGrpIfSaps    Gauge32,
    vRtrMldGrpSrcSummBlkGrpIfSaps    Gauge32
}

vRtrMldGrpSrcSummFwdInterfaces OBJECT-TYPE
    SYNTAX       Gauge32
    MAX-ACCESS   read-only
    STATUS       current
    DESCRIPTION
        "vRtrMldGrpSrcSummFwdInterfaces indicates the number of interfaces
         having this Group/Source combination in the forwarding list."
    ::= { vRtrMldGrpSrcSummaryEntry 1 }

vRtrMldGrpSrcSummBlkInterfaces OBJECT-TYPE
    SYNTAX       Gauge32
    MAX-ACCESS   read-only
    STATUS       current
    DESCRIPTION
        "vRtrMldGrpSrcSummBlkInterfaces indicates the number of interfaces
         having this Group/Source combination in the blocking list."
    ::= { vRtrMldGrpSrcSummaryEntry 2 }

vRtrMldGrpSrcSummFwdHosts OBJECT-TYPE
    SYNTAX       Gauge32
    MAX-ACCESS   read-only
    STATUS       current
    DESCRIPTION
        "vRtrMldGrpSrcSummFwdHosts indicates the number of hosts
         having this Group/Source combination in the forwarding list."
    ::= { vRtrMldGrpSrcSummaryEntry 3 }

vRtrMldGrpSrcSummBlkHosts OBJECT-TYPE
    SYNTAX       Gauge32
    MAX-ACCESS   read-only
    STATUS       current
    DESCRIPTION
        "vRtrMldGrpSrcSummBlkHosts indicates the number of hosts
         having this Group/Source combination in the blocking list."
    ::= { vRtrMldGrpSrcSummaryEntry 4 }

vRtrMldGrpSrcSummFwdGrpIfSaps OBJECT-TYPE
    SYNTAX       Gauge32
    MAX-ACCESS   read-only
    STATUS       current
    DESCRIPTION
        "vRtrMldGrpSrcSummFwdGrpIfSaps indicates the number of Grp If SAP's
         having this Group/Source combination in the forwarding list."
    ::= { vRtrMldGrpSrcSummaryEntry 5 }

vRtrMldGrpSrcSummBlkGrpIfSaps OBJECT-TYPE
    SYNTAX       Gauge32
    MAX-ACCESS   read-only
    STATUS       current
    DESCRIPTION
        "vRtrMldGrpSrcSummBlkGrpIfSaps indicates the number of Grp If SAP's
         having this Group/Source combination in the blocking list."
    ::= { vRtrMldGrpSrcSummaryEntry 6 }

--
--     Notification Objects
--

vRtrMldNotifyQueryVersion OBJECT-TYPE
    SYNTAX     Unsigned32
    MAX-ACCESS accessible-for-notify
    STATUS     current
    DESCRIPTION
        "vRtrMldNotifyQueryVersion is used by vRtrMldIfRxQueryVerMismatch
         to notify the version of the query received by the router."
    ::= { vRtrMldNotificationObjs 1 }

vRtrMldNotifyGrpAddrType OBJECT-TYPE
    SYNTAX     InetAddressType
    MAX-ACCESS accessible-for-notify
    STATUS     current
    DESCRIPTION
        "The value of the object vRtrMldNotifyGrpAddrType indicates
         the type of vRtrMldNotifyGrpAddr."
    ::= { vRtrMldNotificationObjs 2 }

vRtrMldNotifyGrpAddr OBJECT-TYPE
    SYNTAX     InetAddress
    MAX-ACCESS accessible-for-notify 
    STATUS     current
    DESCRIPTION
        "The value of the object vRtrMldNotifyGrpAddr indicates
         the multicast group address."
    ::= { vRtrMldNotificationObjs 3 }

vRtrMldNotifyDescription  OBJECT-TYPE
   SYNTAX       DisplayString
   MAX-ACCESS   accessible-for-notify
   STATUS       current
   DESCRIPTION
       "The object vRtrMldNotifyDescription is a printable character 
        string."
   ::= { vRtrMldNotificationObjs 4 }

vRtrMldNotifyMcacPolicyName  OBJECT-TYPE
   SYNTAX       TPolicyStatementNameOrEmpty
   MAX-ACCESS   accessible-for-notify
   STATUS       current
   DESCRIPTION
       "The value of vRtrMldNotifyMcacPolicyName specifies the name of the
        multicast CAC policy."
   ::= { vRtrMldNotificationObjs 5 }

vRtrMldNotifySrcAddrType OBJECT-TYPE
    SYNTAX     InetAddressType
    MAX-ACCESS accessible-for-notify
    STATUS     current
    DESCRIPTION
        "The value of the object vRtrMldNotifySrcAddrType indicates
         the type of vRtrMldNotifySrcAddr."
    ::= { vRtrMldNotificationObjs 6 }

vRtrMldNotifySrcAddr OBJECT-TYPE
    SYNTAX     InetAddress
    MAX-ACCESS accessible-for-notify 
    STATUS     current
    DESCRIPTION
        "The value of the object vRtrMldNotifySrcAddr indicates
         the multicast source address."
    ::= { vRtrMldNotificationObjs 7 }

--
--     Notification Definition
--

vRtrMldIfRxQueryVerMismatch NOTIFICATION-TYPE
    OBJECTS {
        vRtrID,
        vRtrIfIndex,
        vRtrMldIfAdminVersion,
        vRtrMldNotifyQueryVersion
    }
    STATUS  current
    DESCRIPTION
        "A vRtrMldIfRxQueryVerMismatch notification is generated when the
         MLD interface is configured as MLDv2 but the router receives a 
         MLDv1 Query on the interface.

         vRtrIfIndex will identify the router interface on which the query is
         received. vRtrMldIfAdminVersion will contain the configured
         version of the interface and vRtrMldNotifyQueryVersion
         will contain the version of the received query."
    ::= { vRtrMldNotifications 1 }

vRtrMldIfCModeRxQueryMismatch NOTIFICATION-TYPE
    OBJECTS {
        vRtrID,
        vRtrIfIndex,
        vRtrMldIfOperVersion,
        vRtrMldNotifyQueryVersion
    }
    STATUS  current
    DESCRIPTION
        "A vRtrMldIfCModeRxQueryMismatch notification is generated 
         when there is a mismatch between the compatible mode of the interface
         and the version of the received query.

         It is generated when the MLD interface is in MLDv1 compatible mode 
         but it receives an MLDv2 Query on the interface.

         vRtrIfIndex will identify the router interface on which the query is
         received. vRtrMldIfOperVersion will indicate the compatibility mode
         of the interface and vRtrMldNotifyQueryVersion will contain the 
         version of the received query."
    ::= { vRtrMldNotifications 2 }

vRtrMldMaxGrpsLimitExceeded NOTIFICATION-TYPE
    OBJECTS {
        vRtrMldIfMaxGroups
    }
    STATUS  current
    DESCRIPTION
        "The vRtrMldMaxGrpsLimitExceeded event is generated when an 
         attempt is made to configure a group when vRtrMldIfGroupCount, 
         the number of groups configured on the PIM interface, is equal 
         to vRtrMldIfMaxGroups, the maximum number of groups supported 
         on the system."
    ::= { vRtrMldNotifications 3 }
    
vRtrMldMcacPlcyDropped NOTIFICATION-TYPE
    OBJECTS {
        vRtrMldIfMcacPolicyName,
        vRtrMldNotifyGrpAddrType,
        vRtrMldNotifyGrpAddr,
        vRtrMldNotifySrcAddrType,
        vRtrMldNotifySrcAddr,
        vRtrMldNotifyDescription
    }
    STATUS      current
    DESCRIPTION
        "The vRtrMldMcacPlcyDropped event is generated when an
         MLD group is dropped on a given interface because of 
         applying a multicast CAC policy given by vRtrMldIfMcacPolicyName."
    ::= { vRtrMldNotifications 4 }
     
vRtrMldHostInstantiationFail NOTIFICATION-TYPE
    OBJECTS {
        vRtrMldGrpIfHostLastChangeTime,
        vRtrMldNotifyDescription
    }
    STATUS      current
    DESCRIPTION
        "The vRtrMldHostInstantiationFail event is generated when a
         host is eligible for running MLD, but MLD cannot be started on the host."
    ::= { vRtrMldNotifications 5 }


vRtrMldHostMaxGrpsLimitExceeded NOTIFICATION-TYPE
    OBJECTS {
         vRtrMldHostFwdSvcId,
         vRtrMldHostGrpIfId,
         vRtrMldHostMaxGroups
    }
    STATUS  current
    DESCRIPTION
        "The vRtrMldMaxGrpsLimitExceeded event is generated when an attempt is 
         made to configure a group when vRtrMldHostGroupCount, the number of 
         groups configured on the PIM interface, is equal to vRtrMldHostMaxGroups, 
         the maximum number of groups supported on the host."
    ::= { vRtrMldNotifications 6 }

vRtrMldHostMcacPlcyDropped NOTIFICATION-TYPE
    OBJECTS {
        vRtrMldHostSubscriberId,
        vRtrMldNotifyMcacPolicyName,
        vRtrMldNotifyGrpAddrType,
        vRtrMldNotifyGrpAddr,
        vRtrMldNotifySrcAddrType,
        vRtrMldNotifySrcAddr,
        vRtrMldNotifyDescription
    }
    STATUS      current
    DESCRIPTION
        "The vRtrMldHostMcacPlcyDropped event is generated when an
         MLD group is dropped on a given Host because of 
         applying a multicast CAC policy given by vRtrMldNotifyMcacPolicyName."
    ::= { vRtrMldNotifications 7 }

vRtrMldHostCModeRxQueryMismatch NOTIFICATION-TYPE
    OBJECTS {
        vRtrMldHostOperVersion,
        vRtrMldNotifyQueryVersion
    }
    STATUS  current
    DESCRIPTION
        "A vRtrMldHostCModeRxQueryMismatch notification is generated 
         when there is a mismatch between the compatible mode of the MLD Host
         and the version of the received query.

         It is generated when the Host is in MLDv1 compatible mode 
         but it receives an MLDv2 Query. 

         vRtrMldHostAddress will identify the Host on which the query is
         received. vRtrMldHostOperVersion will indicate the compatibility mode
         of the Host and vRtrMldNotifyQueryVersion will contain the 
         version of the received query."
    ::= { vRtrMldNotifications 8 }

vRtrMldHostRxQueryVerMismatch NOTIFICATION-TYPE
    OBJECTS {
        vRtrMldHostAdminVersion,
        vRtrMldNotifyQueryVersion
    }
    STATUS  current
    DESCRIPTION
        "A vRtrMldHostRxQueryVerMismatch notification is generated when the
         MLD host is configured as MLDv2 but receives a 
         MLDv1 Query.

         vRtrMldHostAddress will identify the Host on which the query is
         received. vRtrMldHostAdminVersion will contain the configured
         version of the Host and vRtrMldNotifyQueryVersion
         will contain the version of the received query."
    ::= { vRtrMldNotifications 9 }

vRtrMldHostMaxSrcsLimitExceeded NOTIFICATION-TYPE
    OBJECTS {
         vRtrMldHostFwdSvcId,
         vRtrMldHostGrpIfId,
         vRtrMldHostMaxSources
    }
    STATUS  current
    DESCRIPTION
        "The vRtrMldHostMaxSrcsLimitExceeded event is generated when an attempt 
         is made to configure a source for a group when the number of sources 
         for this group is equal to vRtrMldHostMaxSources, the maximum number 
         of sources per group supported on the host."
    ::= { vRtrMldNotifications 10 }

vRtrMldMaxSrcsLimitExceeded NOTIFICATION-TYPE
    OBJECTS {
         vRtrMldIfMaxSources
    }
    STATUS  current
    DESCRIPTION
        "The vRtrMldMaxSrcsLimitExceeded event is generated when an attempt 
         is made to configure a source for a group when the number of sources 
         for this group is equal to vRtrMldIfMaxSources, the maximum number 
         of sources per group supported on the interface."
    ::= { vRtrMldNotifications 11 }

vRtrMldGrpIfSapMaxGrpsLimExceed NOTIFICATION-TYPE
    OBJECTS {
         vRtrMldGrpIfSapMaxGroups
    }
    STATUS  current
    DESCRIPTION
        "The vRtrMldGrpIfSapMaxGrpsLimExceed event is generated when an
         attempt is made to configure a group when vRtrMldGrpIfSapGroupCount, 
         the number of groups configured on the SAP, is equal to 
         vRtrMldGrpIfSapMaxGroups, the maximum number of groups supported on
         the SAP."
    ::= { vRtrMldNotifications 12 }

vRtrMldGrpIfSapMaxSrcsLimExceed NOTIFICATION-TYPE
    OBJECTS {
         vRtrMldGrpIfSapMaxSources
    }
    STATUS  current
    DESCRIPTION
        "The vRtrMldGrpIfSapMaxSrcsLimExceed event is generated when an attempt 
         is made to configure a source for a group when the number of sources 
         for this group is equal to vRtrMldGrpIfSapMaxSources, the maximum 
         number of sources per group supported on the SAP."
    ::= { vRtrMldNotifications 13 }

vRtrMldGrpIfSapMcacPlcyDropped NOTIFICATION-TYPE
    OBJECTS {
        vRtrMldGrpIfSapLastChangeTime,
        vRtrMldNotifyMcacPolicyName,
        vRtrMldNotifyGrpAddrType,
        vRtrMldNotifyGrpAddr,
        vRtrMldNotifySrcAddrType,
        vRtrMldNotifySrcAddr,
        vRtrMldNotifyDescription
    }
    STATUS      current
    DESCRIPTION
        "The vRtrMldGrpIfSapMcacPlcyDropped event is generated when an
         MLD group is dropped on a given SAP because of applying a multicast
         CAC policy given by vRtrMldNotifyMcacPolicyName."
    ::= { vRtrMldNotifications 14 }

vRtrMldGrpIfSapCModeRxQueryMism NOTIFICATION-TYPE
    OBJECTS {
        vRtrMldGrpIfSapOperVersion,
        vRtrMldNotifyQueryVersion
    }
    STATUS  current
    DESCRIPTION
        "A vRtrMldGrpIfSapCModeRxQueryMism notification is generated 
         when there is a mismatch between the compatible mode of the MLD SAP
         and the version of the received query.

         It is generated when the SAP is in MLDv1 compatible mode 
         but it receives an MLDv2.

         sapPortId and sapEncapValue will identify the SAP on which the query is
         received. vRtrMldGrpIfSapOperVersion will indicate the compatibility 
         mode of the SAP and vRtrMldNotifyQueryVersion will contain the 
         version of the received query."
    ::= { vRtrMldNotifications 15 }

vRtrMldGrpIfSapRxQueryVerMism NOTIFICATION-TYPE
    OBJECTS {
        vRtrMldGrpIfSapAdminVersion,
        vRtrMldNotifyQueryVersion
    }
    STATUS  current
    DESCRIPTION
        "A vRtrMldGrpIfSapRxQueryVerMism notification is generated when the
         MLD host SAP is configured as MLDv2 but receives a 
         MLDv1 Query.

         sapPortId and sapEncapValue will identify the SAP on which the query is
         received. vRtrMldGrpIfSapAdminVersion will contain the configured
         version of the SAP and vRtrMldNotifyQueryVersion
         will contain the version of the received query."
    ::= { vRtrMldNotifications 16 }

vRtrMldHostMaxGrpSrcsLimitExcd NOTIFICATION-TYPE
    OBJECTS {
         vRtrMldHostFwdSvcId,
         vRtrMldHostGrpIfId,
         vRtrMldHostMaxGrpSources
    }
    STATUS  current
    DESCRIPTION
        "The vRtrMldHostMaxGrpSrcsLimitExcd event is generated when an 
         attempt is made to configure a source for a group when the number of 
         group sources is equal to vRtrMldHostMaxGrpSources, the 
         maximum number of group sources per group supported on the host."
    ::= { vRtrMldNotifications 17 }

vRtrMldMaxGrpSrcsLimitExceeded NOTIFICATION-TYPE
    OBJECTS {
         vRtrMldIfMaxGrpSources
    }
    STATUS  current
    DESCRIPTION
        "The vRtrMldMaxGrpSrcsLimitExceeded event is generated when an attempt 
         is made to configure a group source for a group when the number of
         group sources is equal to vRtrMldIfMaxGrpSources, the 
         maximum number of group sources per group supported on the interface."
    ::= { vRtrMldNotifications 18 }

vRtrMldGrpIfSapMaxGrpSrcLimExcd NOTIFICATION-TYPE
    OBJECTS {
         vRtrMldGrpIfSapMaxGrpSources
    }
    STATUS  current
    DESCRIPTION
        "The vRtrMldGrpIfSapMaxGrpSrcLimExcd event is generated when an
         attempt is made to configure a group source for a group when the number
         of group sources is equal to 
         vRtrMldGrpIfSapMaxGrpSources, the maximum number of group sources per
         group supported on the SAP."
    ::= { vRtrMldNotifications 19 }

vRtrMldHostQryIntervalConflict NOTIFICATION-TYPE
    OBJECTS {
         vRtrMldHostFwdSvcId,
         vRtrMldHostGrpIfId,
         vRtrMldNotifyDescription
    }
    STATUS  current
    DESCRIPTION
        "The vRtrMldHostQryIntervalConflict event is generated when one of the 
         MLD-policy query intervals violates restrictions, we fall back to the 
         node query intervals."
    ::= { vRtrMldNotifications 20 }

--
-- Conformance Information
--
tmnxMldCompliances OBJECT IDENTIFIER ::= { tmnxMldConformance 1 }
tmnxMldGroups      OBJECT IDENTIFIER ::= { tmnxMldConformance 2 }

-- compliance statements
tmnxMldCompliance  MODULE-COMPLIANCE
    STATUS  obsolete
    DESCRIPTION
            "The compliance statement for management of extended the MLD
             protocol on Nokia 77x0 SR series systems."
    MODULE  -- this module
        MANDATORY-GROUPS { 
            tmnxMldGlobalGroup,
            tmnxMldIfGroup,
            tmnxMldNotificationGroup
        }
    ::= { tmnxMldCompliances 1 }

tmnxMldV6v1Compliance  MODULE-COMPLIANCE
    STATUS  obsolete
    DESCRIPTION
            "The compliance statement for management of extended the MLD
             protocol on Nokia 77x0 SR series systems."
    MODULE  -- this module
        MANDATORY-GROUPS { 
            tmnxMldGlobalGroup,
            tmnxMldIfGroup,
            tmnxMldNotificationGroup,
            tmnxMldIfV6v1Group
        }
    ::= { tmnxMldCompliances 2 }

tmnxMldV8v0Compliance  MODULE-COMPLIANCE
    STATUS  obsolete
    DESCRIPTION
            "The compliance statement for management of extended the MLD
             protocol on Nokia 77x0 SR series systems."
    MODULE  -- this module
        MANDATORY-GROUPS { 
            tmnxMldGlobalGroup,
            tmnxMldIfGroup,
            tmnxMldNotificationGroup,
            tmnxMldIfV6v1Group,
            tmnxMldIfV8v0Group
        }
    ::= { tmnxMldCompliances 3 }

tmnxMldV12v0Compliance  MODULE-COMPLIANCE
    STATUS  obsolete
    DESCRIPTION
            "The compliance statement for management of extended MLD
             protocol on Nokia SROS series 12.0 systems."
    MODULE  -- this module
        MANDATORY-GROUPS { 
            tmnxMldGlobalGroup,
            tmnxMldGlobalV12v0Group,
            tmnxMldIfGroup,
            tmnxMldNotificationGroup,
            tmnxMldNotificationV12v0Group,
            tmnxMldIfV6v1Group,
            tmnxMldIfV8v0Group,
            tmnxMldIfV12v0Group
        }
    ::= { tmnxMldCompliances 4 }

tmnxMldV14v0Compliance  MODULE-COMPLIANCE
    STATUS  current
    DESCRIPTION
            "The compliance statement for management of extended MLD
             protocol on Nokia SROS series 14.0 systems."
    MODULE  -- this module
        MANDATORY-GROUPS { 
            tmnxMldGlobalGroup,
            tmnxMldGlobalV12v0Group,
            tmnxMldIfGroup,
            tmnxMldNotificationGroup,
            tmnxMldNotificationV12v0Group,
            tmnxMldIfV6v1Group,
            tmnxMldIfV8v0Group,
            tmnxMldIfV12v0Group,
            tmnxMldIfV14v0Group,
            tmnxMldNotificationV14v0Group
        }
    ::= { tmnxMldCompliances 5 }

-- units of conformance

tmnxMldGlobalGroup   OBJECT-GROUP
    OBJECTS {   vRtrMldGeneralTableLastChanged,
                vRtrMldGenQueryInterval,
                vRtrMldGenLastMembQueryIntvl,
                vRtrMldGenQueryResponseIntvl,
                vRtrMldGenRobustCount,
                vRtrMldGenLastChange,
                vRtrMldGenAdminState,
                vRtrMldGenOperState,
                vRtrMldGrpSrcUpTime,
                vRtrMldSsmTransTableLastChanged,
                vRtrMldSsmTransRowStatus,
                vRtrMldSsmTransLastChanged,
                vRtrMldGenStatsStarGTypes,
                vRtrMldGenStatsSGTypes
            }
    STATUS      current
    DESCRIPTION
        "The group of objects supporting management of extended the MLD general 
         capabilities on Nokia 77x0 SR series systems."
    ::= { tmnxMldGroups 1 }

tmnxMldIfGroup     OBJECT-GROUP
    OBJECTS {   vRtrMldIfTableLastChanged,
                vRtrMldIfRowStatus,
                vRtrMldIfLastChanged,
                vRtrMldIfAdminState,
                vRtrMldIfOperState,
                vRtrMldIfAdminVersion,
                vRtrMldIfOperVersion,
                vRtrMldIfQuerierType,
                vRtrMldIfQuerier,
                vRtrMldIfImportPolicy,
                vRtrMldIfGroupCount,
                vRtrMldIfQuerierUpTime,
                vRtrMldIfQuerierExpiryTime,
                vRtrMldIfNextGenQueryTime,
                vRtrMldIfMaxGroups,
                vRtrMldIfMaxGroupsTillNow,
                vRtrMldIfQueryInterval,
                vRtrMldIfLastMembQueryIntvl,
                vRtrMldIfQueryResponseIntvl,                
                vRtrMldIfGroupType,
                vRtrMldIfGroupUpTime,
                vRtrMldIfGroupExpiryTime,
                vRtrMldIfGroupVer1HostTimer,
                vRtrMldIfGroupMode,
                vRtrMldIfGroupCompatMode,
                vRtrMldIfGroupLstRprtrType,
                vRtrMldIfGroupLastReporter,
                vRtrMldIfGrpSrcExpiryTime,
                vRtrMldIfGrpSrcType,
                vRtrMldIfStatcGrpSrcTblLstChngd,  
                vRtrMldIfStaticGrpSrcRowStatus,
                vRtrMldIfStaticGrpSrcLstChanged,
                vRtrMldIfTxGenQueries,
                vRtrMldIfTxGrpQueries,
                vRtrMldIfTxGrpSrcQueries,
                vRtrMldIfTxV1Reports,
                vRtrMldIfTxV2Reports,
                vRtrMldIfTxLeaves,
                vRtrMldIfTxErrors,
                vRtrMldIfRxGenQueries,
                vRtrMldIfRxGrpQueries,
                vRtrMldIfRxGrpSrcQueries,
                vRtrMldIfRxV1Reports,
                vRtrMldIfRxV2Reports,
                vRtrMldIfRxLeaves,
                vRtrMldIfRxBadLenPkts,
                vRtrMldIfRxBadChecksumPkts,
                vRtrMldIfRxUnknownTypePkts,
                vRtrMldIfRxBadReceiveIfPkts,
                vRtrMldIfRxNonLocal,
                vRtrMldIfRxWrongVersions,
                vRtrMldIfImportPolicyDrops,
                vRtrMldIfRxNoRtrAlertPkts,
                vRtrMldIfRxBadEncodings,
                vRtrMldIfRxPktDrops,
                vRtrMldIfStatsStarGTypes,
                vRtrMldIfStatsSGTypes,
                vRtrMldIfRxLocalScopePkts,
                vRtrMldIfRxRsvdScopePkts
            }
    STATUS        current
    DESCRIPTION
        "The group of objects supporting management of extended the MLD
         interfaces on Nokia 77x0 SR series systems."
    ::= { tmnxMldGroups 2 }

tmnxMldNotifyObjsGroup   OBJECT-GROUP
    OBJECTS {   
               vRtrMldNotifyQueryVersion
            }
    STATUS        current
    DESCRIPTION
        "The group of objects supporting the MLD notifications 
         on Nokia 77x0 SR series systems."
    ::= { tmnxMldGroups 3 }

tmnxMldNotificationGroup NOTIFICATION-GROUP
    NOTIFICATIONS { 
                      vRtrMldIfRxQueryVerMismatch,
                      vRtrMldIfCModeRxQueryMismatch,
                      vRtrMldMaxGrpsLimitExceeded
                  }
    STATUS        current
    DESCRIPTION
        "The group of notifications supporting the MLD feature
         on Nokia 77x0 SR series systems."
    ::= { tmnxMldGroups 4 }

tmnxMldIfV6v1Group     OBJECT-GROUP
    OBJECTS {   vRtrMldIfSsmTltTableLastChanged,
                vRtrMldIfSsmTransRowStatus
            }
    STATUS        current
    DESCRIPTION
        "The group of objects supporting management of SSM Translate
         feature on extended MLD interfaces on 6.1 release Nokia 7xxx
         SR series systems."
    ::= { tmnxMldGroups 5 }

tmnxMldIfV8v0Group     OBJECT-GROUP
    OBJECTS {   vRtrMldIfDisRtrAlertChk
            }
    STATUS        current
    DESCRIPTION
        "The group of objects supporting management of SSM Translate
         feature on extended MLD interfaces on 8.0 release Nokia 7xxx
         SR series systems."
    ::= { tmnxMldGroups 6 }

tmnxMldIfV12v0Group     OBJECT-GROUP
    OBJECTS {
        vRtrMldIfMcacPolicyName         ,
        vRtrMldIfMcacUnconstrainedBW    ,
        vRtrMldIfMcacConstAdminState    ,
        vRtrMldIfMcacPreRsvdMandBW      ,
        vRtrMldIfMcacinUseMandBw        , 
        vRtrMldIfMcacinUseOpnlBw        , 
        vRtrMldIfMcacAvailMandBw        , 
        vRtrMldIfMcacAvailOpnlBw        ,
        vRtrMldIfMcacValuesInTransit    ,
        vRtrMldIfMaxSources             ,
        vRtrMldIfMaxGrpSources          ,
        vRtrMldIfMcacUseLagPortWeight   ,

        vRtrMldIfStatsMcacPolicyDrops   ,

        vRtrMldIfMcacLevelRowStatus     ,
        vRtrMldIfMcacLevelBW            ,

        vRtrMldIfMcacLagRowStatus       ,
        vRtrMldIfMcacLagLevel           ,

        vRtrMldHostLastChangeTime       ,
        vRtrMldHostOperState            ,
        vRtrMldHostOperVersion          ,
        vRtrMldHostGroupCount           ,
        vRtrMldHostNextGenQueryTime     ,
        vRtrMldHostMaxGroupsTillNow     ,
        vRtrMldHostFwdSvcId             ,
        vRtrMldHostGrpIfId              ,
        vRtrMldHostSubscriberId         ,
        vRtrMldHostMldPolicy            ,
        vRtrMldHostMaxGroups            ,
        vRtrMldHostAdminVersion         ,
        vRtrMldHostMaxSources           ,
        vRtrMldHostMaxGrpSources        ,

        vRtrMldHostTxGenQueries         ,
        vRtrMldHostTxGrpQueries         ,
        vRtrMldHostTxGrpSrcQueries      ,
        vRtrMldHostTxV1Reports          , 
        vRtrMldHostTxV2Reports          ,
        vRtrMldHostTxLeaves             ,
        vRtrMldHostTxErrors             ,
        vRtrMldHostRxGenQueries         ,
        vRtrMldHostRxGrpQueries         ,
        vRtrMldHostRxGrpSrcQueries      ,
        vRtrMldHostRxV1Reports          ,
        vRtrMldHostRxV2Reports          ,
        vRtrMldHostRxLeaves             ,
        vRtrMldHostRxBadLenPkts         ,
        vRtrMldHostRxBadChecksumPkts    ,
        vRtrMldHostRxUnknownTypePkts    , 
        vRtrMldHostRxBadReceiveIfPkts   ,
        vRtrMldHostRxNonLocal           ,
        vRtrMldHostRxWrongVersions      ,
        vRtrMldHostImportPolicyDrops    ,
        vRtrMldHostRxNoRtrAlertPkts     ,
        vRtrMldHostRxBadEncodings       ,
        vRtrMldHostRxPktDrops           ,
        vRtrMldHostStatsStarGTypes      ,
        vRtrMldHostStatsSGTypes         ,
        vRtrMldHostStatsMcacPolicyDrops ,
        vRtrMldHostRxLocalScopePkts     ,
        vRtrMldHostRxRsvdScopePkts      ,
        vRtrMldHostRedirectionDrops     ,
        
        vRtrMldGrpIfRowStatus           ,
        vRtrMldGrpIfLastChangeTime      ,
        vRtrMldGrpIfAdminState          ,
        vRtrMldGrpIfOperState           ,
        vRtrMldGrpIfSubHostsOnly        ,                                                        
        vRtrMldGrpIfAdminVersion        ,
        vRtrMldGrpIfImportPolicy        ,
        vRtrMldGrpIfSubnetCheck         ,
        vRtrMldGrpIfMcacPolicyName      ,
        vRtrMldGrpIfMcacUnconstrainedBW ,
        vRtrMldGrpIfMcacConstAdminState ,
        vRtrMldGrpIfMcacPreRsvdMandBW   ,
        vRtrMldGrpIfMcacinUseMandBw     , 
        vRtrMldGrpIfMcacinUseOpnlBw     , 
        vRtrMldGrpIfMcacAvailMandBw     , 
        vRtrMldGrpIfMcacAvailOpnlBw     ,
        vRtrMldGrpIfMcacValuesInTransit ,                                                        
        vRtrMldGrpIfDisRtrAlertChk      ,
        vRtrMldGrpIfMaxGroups           ,
        vRtrMldGrpIfMaxSources          ,
        vRtrMldGrpIfMaxGrpSources       ,       

        vRtrMldGrpIfHostGrpType         ,
        vRtrMldGrpIfHostGrpUpTime       ,
        vRtrMldGrpIfHostGrpExpiryTime   ,
        vRtrMldGrpIfHostGrpVer1HostTmr  ,
        vRtrMldGrpIfHostGrpMode         ,
        vRtrMldGrpIfHostGrpCompatMode   ,
        vRtrMldGrpIfHostGrpMRDstVrId    ,
        vRtrMldGrpIfHostGrpMRDstIfId    ,
        
        vRtrMldGrpIfHostGrpSrcExpTime   ,
        vRtrMldGrpIfHostGrpSrcType      ,
        vRtrMldGrpIfHostGrpSrcMRDstVrId ,
        vRtrMldGrpIfHostGrpSrcMRDstIfId ,
        
        vRtrMldGrpSrcHostUpTime         ,
        
        vRtrMldHostGrpSrcExpiryTime     ,
        vRtrMldHostGrpSrcType           ,
        vRtrMldHostGrpSrcMcRdrDstVRtrID ,
        vRtrMldHostGrpSrcMcRdrDstIfIdx  ,
        
        vRtrMldHostGrpType              ,
        vRtrMldHostGrpUpTime            ,
        vRtrMldHostGrpExpiryTime        ,
        vRtrMldHostGrpVer1HostTmr       ,
        vRtrMldHostGrpMode              ,
        vRtrMldHostGrpCompatMode        ,
        vRtrMldHostGrpMcRdrDstVrId      ,
        vRtrMldHostGrpMcRdrDstIfId      ,
        
        vRtrMldGrpIfHostLastChangeTime  ,
        vRtrMldGrpIfHostOperState       ,
        
        vRtrMldGrpIfSapLastChangeTime   ,
        vRtrMldGrpIfSapOperState        ,
        vRtrMldGrpIfSapAdminVersion     ,
        vRtrMldGrpIfSapOperVersion      ,
        vRtrMldGrpIfSapGroupCount       ,
        vRtrMldGrpIfSapNextGenQueryTime ,
        vRtrMldGrpIfSapMaxGroups        ,
        vRtrMldGrpIfSapMaxGroupsTillNow ,
        vRtrMldGrpIfSapMaxSources       ,
        vRtrMldGrpIfSapMaxGrpSources    ,
        
        vRtrMldGrpIfSapTxGenQueries     ,
        vRtrMldGrpIfSapTxGrpQueries     ,
        vRtrMldGrpIfSapTxGrpSrcQueries  ,
        vRtrMldGrpIfSapTxV1Reports      ,
        vRtrMldGrpIfSapTxV2Reports      ,
        vRtrMldGrpIfSapTxLeaves         ,
        vRtrMldGrpIfSapTxErrors         ,
        vRtrMldGrpIfSapRxGenQueries     ,
        vRtrMldGrpIfSapRxGrpQueries     ,
        vRtrMldGrpIfSapRxGrpSrcQueries  ,
        vRtrMldGrpIfSapRxV1Reports      ,
        vRtrMldGrpIfSapRxV2Reports      ,
        vRtrMldGrpIfSapRxLeaves         ,
        vRtrMldGrpIfSapRxBadLenPkts     ,
        vRtrMldGrpIfSapRxBadChksumPkts  ,
        vRtrMldGrpIfSapRxUnknTypePkts   ,
        vRtrMldGrpIfSapRxBadRecvIfPkts  ,
        vRtrMldGrpIfSapRxNonLocal       ,
        vRtrMldGrpIfSapRxWrongVersions  ,
        vRtrMldGrpIfSapImportPlcyDrops  ,
        vRtrMldGrpIfSapRxNoRtrAlertPkts ,
        vRtrMldGrpIfSapRxBadEncodings   ,
        vRtrMldGrpIfSapRxPktDrops       ,
        vRtrMldGrpIfSapStatsStarGTypes  ,
        vRtrMldGrpIfSapStatsSGTypes     ,
        vRtrMldGrpIfSapStatsMcacPlcyDrp ,
        vRtrMldGrpIfSapRxLocalScopePkts ,
        vRtrMldGrpIfSapRxRsvdScopePkts  ,
        
        vRtrMldGrpIfSapGrpType          ,
        vRtrMldGrpIfSapGrpUpTime        ,
        vRtrMldGrpIfSapGrpExpiryTime    ,
        vRtrMldGrpIfSapGrpVer1HostTmr   ,
        vRtrMldGrpIfSapGrpMode          ,
        vRtrMldGrpIfSapGrpCompatMode    ,
        
        vRtrMldGrpIfSapGrpSrcExpTime    ,
        vRtrMldGrpIfSapGrpSrcType       ,
        
        vRtrMldGrpSrcGrpIfSapUpTime     ,
        
        vRtrMldGrpSrcSummFwdInterfaces   ,
        vRtrMldGrpSrcSummBlkInterfaces   ,
        vRtrMldGrpSrcSummFwdHosts        ,
        vRtrMldGrpSrcSummBlkHosts        ,
        vRtrMldGrpSrcSummFwdGrpIfSaps    ,
        vRtrMldGrpSrcSummBlkGrpIfSaps    ,
        
        vRtrMldGrpIfQrySrcIpAddrType     ,
        vRtrMldGrpIfQrySrcIpAddr
            }
    STATUS        current
    DESCRIPTION
        "The group of objects supporting management of SSM Translate
         feature on extended MLD interfaces on Nokia SROS series
         12.0 systems."
    ::= { tmnxMldGroups 7 }        

tmnxMldNotifyObjsV12v0Group   OBJECT-GROUP
    OBJECTS {   
        vRtrMldNotifyGrpAddrType,
        vRtrMldNotifyGrpAddr,
        vRtrMldNotifyDescription,
        vRtrMldNotifyMcacPolicyName,
        vRtrMldNotifySrcAddrType,
        vRtrMldNotifySrcAddr
            }
    STATUS        current
    DESCRIPTION
        "The group of objects supporting the MLD notifications 
         on Nokia SROS series 12.0 systems."
    ::= { tmnxMldGroups 8 }

tmnxMldNotificationV12v0Group NOTIFICATION-GROUP
    NOTIFICATIONS { 
        vRtrMldMcacPlcyDropped,
        vRtrMldHostInstantiationFail,
        vRtrMldHostMaxGrpsLimitExceeded,
        vRtrMldHostMcacPlcyDropped,
        vRtrMldHostCModeRxQueryMismatch,
        vRtrMldHostRxQueryVerMismatch,
        vRtrMldHostMaxSrcsLimitExceeded,
        vRtrMldMaxSrcsLimitExceeded,
        vRtrMldGrpIfSapMaxGrpsLimExceed,
        vRtrMldGrpIfSapMaxSrcsLimExceed,
        vRtrMldGrpIfSapMcacPlcyDropped,
        vRtrMldGrpIfSapCModeRxQueryMism,
        vRtrMldGrpIfSapRxQueryVerMism,
        vRtrMldHostMaxGrpSrcsLimitExcd,
        vRtrMldMaxGrpSrcsLimitExceeded,
        vRtrMldGrpIfSapMaxGrpSrcLimExcd
                  }
    STATUS        current
    DESCRIPTION
        "The group of notifications supporting the MLD feature
         on Nokia SROS series 12.0 systems."
    ::= { tmnxMldGroups 9 }

tmnxMldGlobalV12v0Group   OBJECT-GROUP
    OBJECTS {   vRtrMldGenGrpIfQrySrcIpAddrType,
                vRtrMldGenGrpIfQrySrcIpAddr
            }
    STATUS      current
    DESCRIPTION
        "The group of objects supporting management of extended the MLD general 
         capabilities on Nokia SROS series systems 12.0 release."
    ::= { tmnxMldGroups 10 }

tmnxMldIfV14v0Group     OBJECT-GROUP
    OBJECTS {
        vRtrMldIfMcacIfPolicyName,
        vRtrMldGrpIfMcacIfPolicyName,
        vRtrMldIfSGrpRangeSrcTblLstChgd,
        vRtrMldIfSGrpRangeSrcRowStatus,
        vRtrMldIfSGrpRangeLastChanged,
        vRtrMldIfSGrpRangeGrpCount,

        vRtrMldGrpIfQueryInterval,
        vRtrMldGrpIfLastLstnrQueryIntvl,
        vRtrMldGrpIfQueryResponseIntvl,
        vRtrMldHostQueryInterval,
        vRtrMldHostLastLstnrQueryIntvl,
        vRtrMldHostQueryResponseIntvl,
        vRtrMldHostDisRtrAlertChk,

        vRtrMldGrpIfSapQryInterval,
        vRtrMldGrpIfSapLastLstnrQryIntvl,
        vRtrMldGrpIfSapQryResponseIntvl
    }
    STATUS        current
    DESCRIPTION
        "The group of objects supporting management of SSM Translate
         feature on extended MLD interfaces on Nokia SROS series
         14.0 systems."
    ::= { tmnxMldGroups 11 }        
tmnxMldNotificationV14v0Group NOTIFICATION-GROUP
    NOTIFICATIONS { 
        vRtrMldHostQryIntervalConflict
    }
    STATUS        current
    DESCRIPTION
        "The group of notifications supporting the MLD feature
         on Nokia SROS series systems 14.0 release."
    ::= { tmnxMldGroups 12 }

END

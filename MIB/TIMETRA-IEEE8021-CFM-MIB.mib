TIMETRA-IEEE8021-CFM-MIB DEFINITIONS ::= BEGIN

IMPORTS
        MODULE-IDENTITY, Unsigned32, OBJECT-TYPE,
        NOTIFICATION-TYPE, Integer32, Counter32,
        Gauge32                                       FROM SNMPv2-SMI

        MODULE-COMPLIANCE, NOTIFICATION-GROUP,
        OBJECT-GROUP                                  FROM SNMPv2-CONF

        MacAddress, RowStatus, TruthValue,
        DisplayString, TEXTUAL-CONVENTION             FROM SNMPv2-TC

        InterfaceIndex, InterfaceIndexOrZero          FROM IF-MIB

        dot1agCfmDefaultMdEntry,
        dot1agCfmMaNetEntry, dot1agCfmMaCompEntry,
        dot1agCfmMaMepListEntry,
        dot1agCfmMdIndex, dot1agCfmMaIndex,
        dot1agCfmMepIdentifier, Dot1agCfmMDLevel,
        Dot1agCfmMpDirection, Dot1agCfmMepIdOrZero,
        Dot1agCfmMepId, VlanIdOrNone,
        Dot1agCfmIdPermission, dot1agCfmMepEntry,
        dot1agCfmMepDbEntry,
        dot1agCfmMepTransmitLbmDestMacAddress,
        dot1agCfmMepTransmitLtmSeqNumber,
        dot1agCfmMdEntry, Dot1agCfmLowestAlarmPri     FROM IEEE8021-CFM-MIB

        LldpChassisIdSubtype                          FROM LLDP-MIB

        timetraSRMIBModules, tmnxSRObjs,
        tmnxSRConfs, tmnxSRNotifyPrefix               FROM TIMETRA-GLOBAL-MIB

        SdpId                                         FROM TIMETRA-SERV-MIB

        TmnxServId, TmnxEnabledDisabled,
        TItemDescription, TNamedItem,
        TmnxCreateOrigin                              FROM TIMETRA-TC-MIB;


timetraIEEE8021CfmMIBModule MODULE-IDENTITY
        LAST-UPDATED "201601010000Z"
        ORGANIZATION "Nokia"
        CONTACT-INFO
            "Nokia SROS Support
             Web: http://www.nokia.com"
        DESCRIPTION
        "This document is the SNMP MIB module to manage and provision dot1ag
        Connectivity Fault Management module functionality for the
        Nokia SROS products. This includes extensions to the
        IEEE8021-CFM MIB.

        Copyright 2008-2016 Nokia. All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."
--
--  Revision History
--
        REVISION        "201601010000Z"
        DESCRIPTION     "Rev 14.0               1 Jan 2016 00:00
                         14.0 release of the TIMETRA-IEEE8021-CFM-MIB."

        REVISION        "201501010000Z"
        DESCRIPTION     "Rev 13.0               1 Jan 2015 00:00
                         13.0 release of the TIMETRA-IEEE8021-CFM-MIB."

        REVISION        "201401010000Z"
        DESCRIPTION     "Rev 12.0               1 Jan 2014 00:00
                         12.0 release of the TIMETRA-IEEE8021-CFM-MIB."

        REVISION        "201102010000Z"
        DESCRIPTION     "Rev 9.0                1 Feb 2011 00:00
                         9.0 release of the TIMETRA-IEEE8021-CFM-MIB."

        REVISION        "200902280000Z"
        DESCRIPTION     "Rev 7.0                28 Feb 2009 00:00
                         7.0 release of the TIMETRA-IEEE8021-CFM-MIB."

        REVISION        "200801010000Z"
        DESCRIPTION     "Rev 1.0                01 Jan 2008 00:00
                         Initial version of the TIMETRA-IEEE8021-CFM-MIB."

        ::= { timetraSRMIBModules 52 }

--%%%%%%%%%%%%%%%%%%%%%%%%%%%%%%%%%%%%%%%%%%%%%%%%%%%%%%%%%%%%%%%%%%%%%%
--
--  Nokia SROS product series IEEE8021-CFM extensions
--

tmnxDot1agMIBObjs                OBJECT IDENTIFIER ::= { tmnxSRObjs 52 }
tmnxDot1agNotificationsPrefix    OBJECT IDENTIFIER ::= { tmnxSRNotifyPrefix 52 }
    tmnxDot1agNotifications
                       OBJECT IDENTIFIER ::= { tmnxDot1agNotificationsPrefix 0 }
tmnxDot1agMIBConformance         OBJECT IDENTIFIER ::= { tmnxSRConfs 52 }

-- Groups in the Nokia CFM MIB Module
tmnxDot1agCfmStack               OBJECT IDENTIFIER ::= { tmnxDot1agMIBObjs 1 }
tmnxDot1agCfmGlobalObjs          OBJECT IDENTIFIER ::= { tmnxDot1agMIBObjs 2 }
tmnxDot1agCfmManagementObjects   OBJECT IDENTIFIER ::= { tmnxDot1agMIBObjs 3 }
tmnxDot1agCfmMd                  OBJECT IDENTIFIER ::= { tmnxDot1agMIBObjs 5 }
tmnxDot1agCfmMa                  OBJECT IDENTIFIER ::= { tmnxDot1agMIBObjs 6 }
tmnxDot1agCfmMep                 OBJECT IDENTIFIER ::= { tmnxDot1agMIBObjs 7 }
tmnxDot1agCfmMip                 OBJECT IDENTIFIER ::= { tmnxDot1agMIBObjs 8 }
tmnxDot1agCfmNotificationObjs    OBJECT IDENTIFIER ::= { tmnxDot1agMIBObjs 9 }
tmnxDot1agCfmDefaultMd           OBJECT IDENTIFIER ::= { tmnxDot1agMIBObjs 10 }

-- ******************************************************************
-- Textual conventions
-- ******************************************************************

Dot1agCfmStatisticOpcodeName     ::= TEXTUAL-CONVENTION
    STATUS      current
    DESCRIPTION
       "An enumerated value indicating the CFM PDU Opcode to which a statistic
        may be associated.

        other(1)              Indicates the CFM PDU type does not match
                              any other type explicitly detailed below.

        ccm(2)                Connectivity check messages.

        lbr(3)                Loopback response messages.

        lbm(4)                Loopback request messages.

        ltr(5)                Linktrace response messages.

        ltm(6)                Linktrace request messages.

        ais(7)                Alarm indication signal messages.

        lck(8)                Ethernet locked signal messages.

        tst(9)                Ethernet test signal messages.

        laps(10)              Linear automatic protection switching messages.

        raps(11)              Ring automatic protection switching messages.

        mcc(12)               Maintenance communications channel messages.

        lmr(13)               Ethernet loss measurement response messages.

        lmm(14)               Ethernet loss measurement messages.

        odm(15)               One way delay measurement messages.

        dmr(16)               Delay measurement response messages.

        dmm(17)               Delay measurement message.

        exr(18)               Ethernet experimental response messages.

        exm(19)               Ethernet experimental messages.

        csf(20)               Client signal fail messages.

        vsr(21)               Vendor specific response messages.

        vsm(22)               Vendor specific messages.

        osl(23)               One way synthetic loss measurement messages.

        slr(24)               Synthetic loss measurement response messages.

        slm(25)               Synthetic loss measurement messages.
       "
    REFERENCE
       "Y.1731 clauses 7 and 8"
    SYNTAX      INTEGER {
                  other(1),
                  ccm(2),
                  lbr(3),
                  lbm(4),
                  ltr(5),
                  ltm(6),
                  ais(7),
                  lck(8),
                  tst(9),
                  laps(10),
                  raps(11),
                  mcc(12),
                  lmr(13),
                  lmm(14),
                  odm(15),
                  dmr(16),
                  dmm(17),
                  exr(18),
                  exm(19),
                  csf(20),
                  vsr(21),
                  vsm(22),
                  osl(23),
                  slr(24),
                  slm(25)
                }

TmnxDot1agCfmMepFclty ::= TEXTUAL-CONVENTION
    STATUS  current
    DESCRIPTION
       "TmnxDot1agCfmMepFclty is an enumerated integer that indicates the
        facility type that a facility MEP has affected.

          value                    indicates 
          -----------------------------------
          port(1)                  physical port
          lag (2)                  lag port
          networkInterface(3)      network interface
          qinqPortTunnelSap(4)     QinQ on physical port
          qinqLagTunnelSap(5)      QinQ on lag port
       "
    SYNTAX      INTEGER {
                    port                     (1),
                    lag                      (2),
                    networkInterface         (3),
                    qinqPortTunnelSap        (4),
                    qinqLagTunnelSap         (5)
                }

--
--
-- Nokia SROS product series dot1ag CFM SDP-Bind Stack Table
--
-- This table is a mirror of the dot1agCfmStackTable in IEEE8021-CFM-MIB.
--
-- The indexes of this table differ from that of the dot1agCfmStackTable
-- by the replacement of the dot1agCfmStackIfIndex and
-- dot1agCfmStackVlanIdOrNone indexes with that of the
-- tmnxDot1agCfmSdpBindStackSdpid and tmnxDot1agCfmSdpBindStackVcId indexes.

-- The CFM SDP-Bind Stack Table

tmnxDot1agCfmSdpBindStackTable   OBJECT-TYPE
    SYNTAX     SEQUENCE OF TmnxDot1agCfmSdpBindStackEntry
    MAX-ACCESS not-accessible
    STATUS     current
    DESCRIPTION
       "There is one CFM SDP-Bind Stack table per bridge. It permits
        the retrieval of information about the Maintenance Points
        configured on any given SDP bindings."
    REFERENCE
       "802.1ag clauses 12.14.2"
    ::= { tmnxDot1agCfmStack 1 }

tmnxDot1agCfmSdpBindStackEntry   OBJECT-TYPE
    SYNTAX     TmnxDot1agCfmSdpBindStackEntry
    MAX-ACCESS not-accessible
    STATUS     current
    DESCRIPTION
       "A conceptual row in the tmnxDot1agCfmSdpBindStackTable. This row behaves
        exactly like the dot1agCfmStackEntry row."
    INDEX { tmnxDot1agCfmSdpBindStackSdpId,
            tmnxDot1agCfmSdpBindStackVcId,
            tmnxDot1agCfmSdpBindStackMdLevel,
            tmnxDot1agCfmSdpBindStackDirection
          }
    ::= { tmnxDot1agCfmSdpBindStackTable 1 }

TmnxDot1agCfmSdpBindStackEntry   ::= SEQUENCE {
      tmnxDot1agCfmSdpBindStackSdpId         SdpId,
      tmnxDot1agCfmSdpBindStackVcId          Unsigned32,
      tmnxDot1agCfmSdpBindStackMdLevel       Dot1agCfmMDLevel,
      tmnxDot1agCfmSdpBindStackDirection     Dot1agCfmMpDirection,
      tmnxDot1agCfmSdpBindStackMdIndex       Unsigned32,
      tmnxDot1agCfmSdpBindStackMaIndex       Unsigned32,
      tmnxDot1agCfmSdpBindStackMepId         Dot1agCfmMepIdOrZero,
      tmnxDot1agCfmSdpBindStackMacAddress    MacAddress
    }

tmnxDot1agCfmSdpBindStackSdpId   OBJECT-TYPE
    SYNTAX     SdpId
    MAX-ACCESS not-accessible
    STATUS     current
    DESCRIPTION
       "The value of tmnxDot1agCfmSdpBindStackSdpId specifies the
        Bridge Port or aggregated port on which MEPs or MHFs
        might be configured."
    REFERENCE
       "802.1ag clause 12.14.2.1.2:a"
    ::= { tmnxDot1agCfmSdpBindStackEntry 1 }

tmnxDot1agCfmSdpBindStackVcId    OBJECT-TYPE
    SYNTAX     Unsigned32
    MAX-ACCESS not-accessible
    STATUS     current
    DESCRIPTION
       "The value of tmnxDot1agCfmSdpBindStackVcId specifies, along with
        tmnxDot1agCfmSdpBindStackSdpId, the SDP Binding for the bridge."
    REFERENCE
       "802.1ag clause 12.14.2.1.2:d"
    ::= { tmnxDot1agCfmSdpBindStackEntry 2 }

tmnxDot1agCfmSdpBindStackMdLevel OBJECT-TYPE
    SYNTAX     Dot1agCfmMDLevel
    MAX-ACCESS not-accessible
    STATUS     current
    DESCRIPTION
       "The value of tmnxDot1agCfmSdpBindStackMdLevel specifies the MD Level of
        the Maintenance Point."
    REFERENCE
       "802.1ag clause 12.14.2.1.2:b"
    ::= { tmnxDot1agCfmSdpBindStackEntry 3 }

tmnxDot1agCfmSdpBindStackDirection OBJECT-TYPE
    SYNTAX     Dot1agCfmMpDirection
    MAX-ACCESS not-accessible
    STATUS     current
    DESCRIPTION
       "The value of tmnxDot1agCfmSdpBindStackDirection specifies the
        Direction in which the MP faces on the Bridge Port"
    REFERENCE
       "802.1ag clause 12.14.2.1.2:c"
    ::= { tmnxDot1agCfmSdpBindStackEntry 4 }

tmnxDot1agCfmSdpBindStackMdIndex OBJECT-TYPE
    SYNTAX     Unsigned32
    MAX-ACCESS read-only
    STATUS     current
    DESCRIPTION
       "The value of tmnxDot1agCfmSdpBindStackMdIndex indicates the index
        of the Maintenance Domain in the dot1agCfmMdTable to which the
        MP is associated, or 0, if none."
    REFERENCE
       "802.1ag clause 12.14.2.1.3:b"
    ::= { tmnxDot1agCfmSdpBindStackEntry 5 }

tmnxDot1agCfmSdpBindStackMaIndex OBJECT-TYPE
    SYNTAX     Unsigned32
    MAX-ACCESS read-only
    STATUS     current
    DESCRIPTION
       "The value of tmnxDot1agCfmSdpBindStackMaIndex indicates the index
        of the MA in the dot1agCfmMaNetTable and dot1agCfmMaCompTable
        to which the MP is associated, or 0, if none."
    REFERENCE
       "802.1ag clause 12.14.2.1.3:c"
    ::= { tmnxDot1agCfmSdpBindStackEntry 6 }

tmnxDot1agCfmSdpBindStackMepId   OBJECT-TYPE
    SYNTAX     Dot1agCfmMepIdOrZero
    MAX-ACCESS read-only
    STATUS     current
    DESCRIPTION
       "The value of tmnxDot1agCfmSdpBindStackMepId indicates if an MEP
        is configured, the MEPID, else 0"
    REFERENCE
       "802.1ag clause 12.14.2.1.3:d"
    ::= { tmnxDot1agCfmSdpBindStackEntry 7 }

tmnxDot1agCfmSdpBindStackMacAddress OBJECT-TYPE
    SYNTAX     MacAddress
    MAX-ACCESS read-only
    STATUS     current
    DESCRIPTION
       "The value of tmnxDot1agCfmSdpBindStackMacAddress indicates
        the MAC address of the MP."
    REFERENCE
      "802.1ag clause 12.14.2.1.3:e"
    ::= { tmnxDot1agCfmSdpBindStackEntry 8 }

-- ******************************************************************
-- The Stack Object. This group will contain all the MIBs objects
-- needed to access the Stack managed object. This group supersedes
-- the dot1agCfmStackTable due to the inclusion of Q-in-Q
-- encapsulation. the VlanIdOrNone object has been expanded to
-- support the full-range of Vlan/Q-in-Q encapsulation. Otherwise
-- this group behaves identically to that of the standard
-- dot1agCfmStackTable.
-- ******************************************************************

-- *****************************************************************
-- The CFM Stack Table
-- ******************************************************************

tmnxDot1agCfmStackTable          OBJECT-TYPE
    SYNTAX     SEQUENCE OF TmnxDot1agCfmStackEntry
    MAX-ACCESS not-accessible
    STATUS     current
    DESCRIPTION
       "There is one CFM Stack table per bridge. It permits
        the retrieval of information about the Maintenance Points
        configured on any given interface.
       "
    REFERENCE
       "802.1ag clauses 12.14.2"
    ::= { tmnxDot1agCfmStack 2 }

tmnxDot1agCfmStackEntry          OBJECT-TYPE
    SYNTAX     TmnxDot1agCfmStackEntry
    MAX-ACCESS not-accessible
    STATUS     current
    DESCRIPTION
       "The Stack table entry"
    INDEX { tmnxDot1agCfmStackifIndex, tmnxDot1agCfmStackVlanIdOrNone,
            tmnxDot1agCfmStackMdLevel, tmnxDot1agCfmStackDirection
          }
    ::= { tmnxDot1agCfmStackTable 1 }

TmnxDot1agCfmStackEntry          ::= SEQUENCE {
      tmnxDot1agCfmStackifIndex       InterfaceIndex,
      tmnxDot1agCfmStackVlanIdOrNone  Unsigned32,
      tmnxDot1agCfmStackMdLevel       Dot1agCfmMDLevel,
      tmnxDot1agCfmStackDirection     Dot1agCfmMpDirection,
      tmnxDot1agCfmStackMdIndex       Unsigned32,
      tmnxDot1agCfmStackMaIndex       Unsigned32,
      tmnxDot1agCfmStackMepId         Dot1agCfmMepIdOrZero,
      tmnxDot1agCfmStackMacAddress    MacAddress,
      tmnxDot1agCfmStackMPType        INTEGER
    }

tmnxDot1agCfmStackifIndex        OBJECT-TYPE
    SYNTAX     InterfaceIndex
    MAX-ACCESS not-accessible
    STATUS     current
    DESCRIPTION
       "This object represents the  Bridge Port or aggregated port
        on which MEPs or MHFs might be configured.

        Upon a restart of the system, the system SHALL, if necessary,
        change the value of this variable, and  rearrange the
        dot1agCfmStackTable, so that it indexes the entry in the
        interface table with the same value of ifAlias that it
        indexed before the system restart.  If no such entry exists,
        then the system SHALL delete all entries in the
        dot1agCfmStackTable with the interface index.
       "
    REFERENCE
       "802.1ag clause 12.14.2.1.2:a"
    ::= { tmnxDot1agCfmStackEntry 1 }

tmnxDot1agCfmStackVlanIdOrNone   OBJECT-TYPE
    SYNTAX     Unsigned32
    MAX-ACCESS not-accessible
    STATUS     current
    DESCRIPTION
       "VLAN ID to which the MP is attached, or 0, if none."
    REFERENCE
       "802.1ag clauses 12.14.2.1.2:d, 22.1.7"
    ::= { tmnxDot1agCfmStackEntry 2 }

tmnxDot1agCfmStackMdLevel        OBJECT-TYPE
    SYNTAX     Dot1agCfmMDLevel
    MAX-ACCESS not-accessible
    STATUS     current
    DESCRIPTION
       "MD Level of the Maintenance Point."
    REFERENCE
       "802.1ag clause 12.14.2.1.2:b"
    ::= { tmnxDot1agCfmStackEntry 3 }

tmnxDot1agCfmStackDirection      OBJECT-TYPE
    SYNTAX     Dot1agCfmMpDirection
    MAX-ACCESS not-accessible
    STATUS     current
    DESCRIPTION
       "Direction in which the MP faces on the Bridge Port"
    REFERENCE
       "802.1ag clause 12.14.2.1.2:c"
    ::= { tmnxDot1agCfmStackEntry 4 }

tmnxDot1agCfmStackMdIndex        OBJECT-TYPE
    SYNTAX     Unsigned32
    MAX-ACCESS read-only
    STATUS     current
    DESCRIPTION
       "The index of the Maintenance Domain in the dot1agCfmMdTable
        to which the MP is associated, or 0, if none."
    REFERENCE
       "802.1ag clause 12.14.2.1.3:b"
    ::= { tmnxDot1agCfmStackEntry 5 }

tmnxDot1agCfmStackMaIndex        OBJECT-TYPE
    SYNTAX     Unsigned32
    MAX-ACCESS read-only
    STATUS     current
    DESCRIPTION
       "The index of the MA in the dot1agCfmMaNetTable and
        dot1agCfmMaCompTable to which the MP is associated, or 0, if
        none."
    REFERENCE
       "802.1ag clause 12.14.2.1.3:c"
    ::= { tmnxDot1agCfmStackEntry 6 }

tmnxDot1agCfmStackMepId          OBJECT-TYPE
    SYNTAX     Dot1agCfmMepIdOrZero
    MAX-ACCESS read-only
    STATUS     current
    DESCRIPTION
       "If an MEP is configured, the MEPID, else 0"
    REFERENCE
       "802.1ag clause 12.14.2.1.3:d"
    ::= { tmnxDot1agCfmStackEntry 7 }

tmnxDot1agCfmStackMacAddress     OBJECT-TYPE
    SYNTAX     MacAddress
    MAX-ACCESS read-only
    STATUS     current
    DESCRIPTION
       "MAC address of the MP."
    REFERENCE
      "802.1ag clause 12.14.2.1.3:e"
    ::= { tmnxDot1agCfmStackEntry 8 }

tmnxDot1agCfmStackMPType         OBJECT-TYPE
    SYNTAX      INTEGER {
                     sap          (1),
                     ethTun       (2),
                     ethRing      (3),
                     facPort      (4),
                     facInterface (5)
                }
    MAX-ACCESS  read-only
    STATUS      current
    DESCRIPTION
        "The value of tmnxDot1agCfmStackMPType indicates the entity that the
         MP is configured on:
              sap(1)          MP is configured on a SAP
              ethTun(2)       MP is configured on an ethernet-tunnel
              ethRing(3)      MP is configured on an ethernet-ring
              facPort(4)      MP is configured on a facility port
              facInterface(5) MP is configured on a facility interface"
    ::= { tmnxDot1agCfmStackEntry 9 }

--
-- Nokia SROS product series dot1ag CFM Virtual MEP Stack Table
--
-- This table is a mirror of the dot1agCfmStackTable in IEEE8021-CFM-MIB.
--
-- The indexes of this table differ from that of the dot1agCfmStackTable
-- by the replacement of the dot1agCfmStackIfIndex and
-- dot1agCfmStackVlanIdOrNone indexes with that of the
-- tmnxDot1agCfmVStackSvcId index.

-- The CFM Virtual Stack Table

tmnxDot1agCfmVStackTable         OBJECT-TYPE
    SYNTAX     SEQUENCE OF TmnxDot1agCfmVStackEntry
    MAX-ACCESS not-accessible
    STATUS     current
    DESCRIPTION
       "There is one CFM Virtual Stack entry per service. It permits
        the retrieval of information about the Maintenance Points
        configured on any given virtual Maintenance Association End
        Point (MEP)."
    REFERENCE
       "802.1ag clauses 12.14.2"
    ::= { tmnxDot1agCfmStack 3 }

tmnxDot1agCfmVStackEntry         OBJECT-TYPE
    SYNTAX     TmnxDot1agCfmVStackEntry
    MAX-ACCESS not-accessible
    STATUS     current
    DESCRIPTION
       "A conceptual row in the tmnxDot1agCfmVStackTable.

        There exists one row for each configured virtual MEP in the system.
        Rows are created and destroyed based on the existence of a virtual MEP."
    INDEX { tmnxDot1agCfmVStackSvcId,
            tmnxDot1agCfmVStackMdLevel,
            tmnxDot1agCfmVStackDirection
          }
    ::= { tmnxDot1agCfmVStackTable 1 }

TmnxDot1agCfmVStackEntry         ::= SEQUENCE {
      tmnxDot1agCfmVStackSvcId         TmnxServId,
      tmnxDot1agCfmVStackMdLevel       Dot1agCfmMDLevel,
      tmnxDot1agCfmVStackDirection     Dot1agCfmMpDirection,
      tmnxDot1agCfmVStackMdIndex       Unsigned32,
      tmnxDot1agCfmVStackMaIndex       Unsigned32,
      tmnxDot1agCfmVStackMepId         Dot1agCfmMepIdOrZero,
      tmnxDot1agCfmVStackMacAddress    MacAddress
    }

tmnxDot1agCfmVStackSvcId         OBJECT-TYPE
    SYNTAX     TmnxServId
    MAX-ACCESS not-accessible
    STATUS     current
    DESCRIPTION
       "The value of tmnxDot1agCfmVStackSvcId specifies the
        service on which MEPs might be configured."
    REFERENCE
       "802.1ag clause 12.14.2.1.2:a"
    ::= { tmnxDot1agCfmVStackEntry 1 }

tmnxDot1agCfmVStackMdLevel       OBJECT-TYPE
    SYNTAX     Dot1agCfmMDLevel
    MAX-ACCESS not-accessible
    STATUS     current
    DESCRIPTION
       "The value of tmnxDot1agCfmVStackMdLevel specifies the Maintenance
       Domain (MD) Level of the Maintenance Point."
    REFERENCE
       "802.1ag clause 12.14.2.1.2:b"
    ::= { tmnxDot1agCfmVStackEntry 2 }

tmnxDot1agCfmVStackDirection     OBJECT-TYPE
    SYNTAX     Dot1agCfmMpDirection
    MAX-ACCESS not-accessible
    STATUS     current
    DESCRIPTION
       "The value of tmnxDot1agCfmVStackDirection specifies the
        direction in which the Maintenance Point (MP) faces on the service."
    REFERENCE
       "802.1ag clause 12.14.2.1.2:c"
    ::= { tmnxDot1agCfmVStackEntry 3 }

tmnxDot1agCfmVStackMdIndex       OBJECT-TYPE
    SYNTAX     Unsigned32
    MAX-ACCESS read-only
    STATUS     current
    DESCRIPTION
       "The value of tmnxDot1agCfmVStackMdIndex indicates the index
        of the Maintenance Domain in the dot1agCfmMdTable to which the
        Maintenance Point (MP) is associated, or 0, if none."
    REFERENCE
       "802.1ag clause 12.14.2.1.3:b"
    ::= { tmnxDot1agCfmVStackEntry 4 }

tmnxDot1agCfmVStackMaIndex       OBJECT-TYPE
    SYNTAX     Unsigned32
    MAX-ACCESS read-only
    STATUS     current
    DESCRIPTION
       "The value of tmnxDot1agCfmVStackMaIndex indicates the index
        of the Maintenance Association (MA) in the dot1agCfmMaNetTable
        and dot1agCfmMaCompTable to which the Maintenance Point (MP) is
        associated, or 0, if none."
    REFERENCE
       "802.1ag clause 12.14.2.1.3:c"
    ::= { tmnxDot1agCfmVStackEntry 5 }

tmnxDot1agCfmVStackMepId         OBJECT-TYPE
    SYNTAX     Dot1agCfmMepIdOrZero
    MAX-ACCESS read-only
    STATUS     current
    DESCRIPTION
       "The value of tmnxDot1agCfmVStackMepId indicates if an MEP
        is configured, the MEPID, else 0."
    REFERENCE
       "802.1ag clause 12.14.2.1.3:d"
    ::= { tmnxDot1agCfmVStackEntry 6 }

tmnxDot1agCfmVStackMacAddress    OBJECT-TYPE
    SYNTAX     MacAddress
    MAX-ACCESS read-only
    STATUS     current
    DESCRIPTION
       "The value of tmnxDot1agCfmVStackMacAddress indicates
        the MAC address of the MP."
    REFERENCE
      "802.1ag clause 12.14.2.1.3:e"
    ::= { tmnxDot1agCfmVStackEntry 7 }


-- ******************************************************************
-- The Primary VLAN Stack Object. This group will contain all the MIBs
-- objects needed to access the Stack managed object. This group
-- supersedes the dot1agCfmStackTable due to the inclusion of the
-- Primary VLAN index.
-- ******************************************************************

-- *****************************************************************
-- The CFM Primary VLAN Stack Table
-- ******************************************************************

tmnxDot1agCfmPVStackTable        OBJECT-TYPE
    SYNTAX     SEQUENCE OF TmnxDot1agCfmPVStackEntry
    MAX-ACCESS not-accessible
    STATUS     current
    DESCRIPTION
       "There is one CFM Stack table per bridge. It permits the retrieval of
        information about the Maintenance Points (MP) configured on any given
        interface."
    REFERENCE
       "802.1ag clauses 12.14.2"
    ::= { tmnxDot1agCfmStack 4 }

tmnxDot1agCfmPVStackEntry        OBJECT-TYPE
    SYNTAX     TmnxDot1agCfmPVStackEntry
    MAX-ACCESS not-accessible
    STATUS     current
    DESCRIPTION
       "The Primary VLAN-ID Stack table entry. Entries in this table are MEPs
        configured to use the primary VLAN-ID of the Maintenance Association
        (MA)."
    INDEX { tmnxDot1agCfmPVStackifIndex,
            tmnxDot1agCfmPVStackVlanIdOrNone,
            tmnxDot1agCfmPVStackPriVlanId,
            tmnxDot1agCfmPVStackMdLevel,
            tmnxDot1agCfmPVStackDirection
          }
    ::= { tmnxDot1agCfmPVStackTable 1 }

TmnxDot1agCfmPVStackEntry        ::= SEQUENCE {
    tmnxDot1agCfmPVStackifIndex      InterfaceIndex,
    tmnxDot1agCfmPVStackVlanIdOrNone Unsigned32,
    tmnxDot1agCfmPVStackPriVlanId    Unsigned32,
    tmnxDot1agCfmPVStackMdLevel      Dot1agCfmMDLevel,
    tmnxDot1agCfmPVStackDirection    Dot1agCfmMpDirection,
    tmnxDot1agCfmPVStackMdIndex      Unsigned32,
    tmnxDot1agCfmPVStackMaIndex      Unsigned32,
    tmnxDot1agCfmPVStackMepId        Dot1agCfmMepIdOrZero,
    tmnxDot1agCfmPVStackMacAddress   MacAddress
}

tmnxDot1agCfmPVStackifIndex      OBJECT-TYPE
    SYNTAX     InterfaceIndex
    MAX-ACCESS not-accessible
    STATUS     current
    DESCRIPTION
       "This object represents the  Bridge Port or aggregated port
        on which MEPs or MHFs might be configured."
    REFERENCE
       "802.1ag clause 12.14.2.1.2:a"
    ::= { tmnxDot1agCfmPVStackEntry 1 }

tmnxDot1agCfmPVStackVlanIdOrNone OBJECT-TYPE
    SYNTAX     Unsigned32
    MAX-ACCESS not-accessible
    STATUS     current
    DESCRIPTION
       "VLAN ID to which the MP is attached, or 0, if none."
    REFERENCE
       "802.1ag clauses 12.14.2.1.2:d, 22.1.7"
    ::= { tmnxDot1agCfmPVStackEntry 2 }

tmnxDot1agCfmPVStackPriVlanId    OBJECT-TYPE
    SYNTAX     Unsigned32
    MAX-ACCESS not-accessible
    STATUS     current
    DESCRIPTION
       "The Primary VLAN ID with which the Maintenance Association is
        associated."
    REFERENCE
       "802.1ag clause 12.14.6.1.3:b"
    ::= { tmnxDot1agCfmPVStackEntry 3 }

tmnxDot1agCfmPVStackMdLevel      OBJECT-TYPE
    SYNTAX     Dot1agCfmMDLevel
    MAX-ACCESS not-accessible
    STATUS     current
    DESCRIPTION
       "MD Level of the Maintenance Point."
    REFERENCE
       "802.1ag clause 12.14.2.1.2:b"
    ::= { tmnxDot1agCfmPVStackEntry 4 }

tmnxDot1agCfmPVStackDirection    OBJECT-TYPE
    SYNTAX     Dot1agCfmMpDirection
    MAX-ACCESS not-accessible
    STATUS     current
    DESCRIPTION
       "Direction in which the MP faces on the Bridge Port"
    REFERENCE
       "802.1ag clause 12.14.2.1.2:c"
    ::= { tmnxDot1agCfmPVStackEntry 5 }

tmnxDot1agCfmPVStackMdIndex      OBJECT-TYPE
    SYNTAX     Unsigned32
    MAX-ACCESS read-only
    STATUS     current
    DESCRIPTION
       "The index of the Maintenance Domain in the dot1agCfmMdTable
        to which the MP is associated, or 0, if none."
    REFERENCE
       "802.1ag clause 12.14.2.1.3:b"
    ::= { tmnxDot1agCfmPVStackEntry 6 }

tmnxDot1agCfmPVStackMaIndex      OBJECT-TYPE
    SYNTAX     Unsigned32
    MAX-ACCESS read-only
    STATUS     current
    DESCRIPTION
       "The index of the MA in the dot1agCfmMaNetTable and
        dot1agCfmMaCompTable to which the MP is associated, or 0, if
        none."
    REFERENCE
       "802.1ag clause 12.14.2.1.3:c"
    ::= { tmnxDot1agCfmPVStackEntry 7 }

tmnxDot1agCfmPVStackMepId        OBJECT-TYPE
    SYNTAX     Dot1agCfmMepIdOrZero
    MAX-ACCESS read-only
    STATUS     current
    DESCRIPTION
       "If an MEP is configured, the MEPID, else 0"
    REFERENCE
       "802.1ag clause 12.14.2.1.3:d"
    ::= { tmnxDot1agCfmPVStackEntry 8 }

tmnxDot1agCfmPVStackMacAddress   OBJECT-TYPE
    SYNTAX     MacAddress
    MAX-ACCESS read-only
    STATUS     current
    DESCRIPTION
       "MAC address of the MP."
    REFERENCE
      "802.1ag clause 12.14.2.1.3:e"
    ::= { tmnxDot1agCfmPVStackEntry 9 }

--
-- Nokia SROS product series dot1ag CFM MA Table
--
-- This table AUGMENTS the dot1agCfmMaNetTable in IEEE8021-CFM-MIB.
--
-- The CFM Maintenance Association Table
tmnxDot1agCfmMaNetTable          OBJECT-TYPE
    SYNTAX      SEQUENCE OF TmnxDot1agCfmMaNetEntry
    MAX-ACCESS  not-accessible
    STATUS      current
    DESCRIPTION
        "The tmnxDot1agCfmMaNetTable AUGMENTS the standard MIB table,
         dot1agCfmMaNetTable. This table is used to enhance Maintenance
         Association functionality for Ethernet Connectivity Fault Management
         (ETH-CFM)."
    ::= { tmnxDot1agCfmMa 1 }

tmnxDot1agCfmMaNetEntry          OBJECT-TYPE
    SYNTAX      TmnxDot1agCfmMaNetEntry
    MAX-ACCESS  not-accessible
    STATUS      current
    DESCRIPTION
        "The tmnxDot1agCfmMaNetEntry consists of the configuration objects
         used to enhance the Maintenance Association functionality."
    AUGMENTS { dot1agCfmMaNetEntry }
    ::= { tmnxDot1agCfmMaNetTable 1 }

TmnxDot1agCfmMaNetEntry          ::= SEQUENCE {
    tmnxDot1agCfmMaNetHoldDownTimer  Unsigned32,
    tmnxDot1agCfmMaNetTotalMEPCount  Counter32,
    tmnxDot1agCfmMaNetAutoDiscAdmin  TruthValue,
    tmnxDot1agCfmMaNetIdPermission   Dot1agCfmIdPermission
}

tmnxDot1agCfmMaNetHoldDownTimer  OBJECT-TYPE
    SYNTAX      Unsigned32 (0|1..1000)
    UNITS       "centiseconds"
    MAX-ACCESS  read-create
    STATUS      current
    DESCRIPTION
        "The value of tmnxDot1agCfmMaNetHoldDownTimer specifies the time, in
         centiseconds, that a MEP in the association will delay declaring a
         fault.  This delay is added on to the existing
         3.5 * dot1agCfmMaNetCcmInterval value used to determine if a
         connectivity fault to the peer should be raised.

         A value of zero (0) indicates that no additional delay should be
         added to the existing 3.5 * dot1agCfmMaNetCcmInterval value."
    DEFVAL { 0 }
    ::= { tmnxDot1agCfmMaNetEntry 1 }

tmnxDot1agCfmMaNetTotalMEPCount  OBJECT-TYPE
    SYNTAX      Counter32
    MAX-ACCESS  read-only
    STATUS      current
    DESCRIPTION
        "The value of tmnxDot1agCfmMaNetTotalMEPCount indicates the number of
        unique MEPs configured (both local and remote) that are associated with
        this MA.

        When the number of MEPs exceed the normal MA limits, the MA is
        considered to be an extended MA and will use a resource from the
        'Extended MA' resource entry in tmnxDot1agCfmComponentLimitTable."
    ::= { tmnxDot1agCfmMaNetEntry 2 }

tmnxDot1agCfmMaNetAutoDiscAdmin  OBJECT-TYPE
    SYNTAX      TruthValue
    MAX-ACCESS  read-create
    STATUS      current
    DESCRIPTION
        "The value of tmnxDot1agCfmMaNetAutoDiscAdmin specifies if remote MEP
         automatic discovery is enabled in the association.  A value of 'true'
         indicates that a new remote MEP entry will be added to the
         dot1agCfmMepDbTable when the node receives a CCM PDU from a remote
         MEP that is not yet in that table (up to the maximum limit of MEPs
         allowed in the association).  A value of 'false' indicates that remote
         MEPs must be manually configured in the association
         dot1agCfmMaMepListTable before being added to the association
         dot1agCfmMepDbTable."
    DEFVAL { false }
    ::= { tmnxDot1agCfmMaNetEntry 3 }

tmnxDot1agCfmMaNetIdPermission   OBJECT-TYPE
    SYNTAX      Dot1agCfmIdPermission
    MAX-ACCESS  read-create
    STATUS      current
    DESCRIPTION
       "Enumerated value indicating what, if anything, is to be included in the
        Sender ID TLV (21.5.3) transmitted by MPs configured in this MA. This
        object is configurable on MA entries that do not consist of component
        entries."
    REFERENCE
       "802.1ag clause 12.14.6.1.3:d"
    DEFVAL { sendIdNone }
    ::= { tmnxDot1agCfmMaNetEntry 4 }

-- The CFM Maintenance Association Component Table
tmnxDot1agCfmMaCompTable         OBJECT-TYPE
    SYNTAX      SEQUENCE OF TmnxDot1agCfmMaCompEntry
    MAX-ACCESS  not-accessible
    STATUS      current
    DESCRIPTION
        "The tmnxDot1agCfmMaCompTable AUGMENTS the standard MIB table,
         dot1agCfmMaCompTable. This table is used to enhance Maintenance
         Association functionality for Ethernet Connectivity Fault Management
         (ETH-CFM)."
    ::= { tmnxDot1agCfmMa 2 }

tmnxDot1agCfmMaCompEntry         OBJECT-TYPE
    SYNTAX      TmnxDot1agCfmMaCompEntry
    MAX-ACCESS  not-accessible
    STATUS      current
    DESCRIPTION
        "The tmnxDot1agCfmMaCompEntry consists of the configuration objects
         used to enhance the Maintenance Association functionality."
    AUGMENTS { dot1agCfmMaCompEntry }
    ::= { tmnxDot1agCfmMaCompTable 1 }

TmnxDot1agCfmMaCompEntry         ::= SEQUENCE {
    tmnxDot1agCfmMaCompMipLtrPrio    Unsigned32
}

tmnxDot1agCfmMaCompMipLtrPrio    OBJECT-TYPE
    SYNTAX     Unsigned32 (0..7)
    MAX-ACCESS read-create
    STATUS     current
    DESCRIPTION
        "The value of tmnxDot1agCfmMaCompMipLtrPrio specifies at what priority
         the link-trace response frames should be transmitted for a MIP
         request."
    DEFVAL { 7 }
    ::= { tmnxDot1agCfmMaCompEntry  1 }

-- Nokia SROS product series CFM MA MEP list table
--
-- The MEP list table augments the standard dot1agCfmMaMepListTable
--
-- ******************************************************************
--  The MEP List Table
-- ******************************************************************

tmnxDot1agCfmMaMepListTable      OBJECT-TYPE
    SYNTAX      SEQUENCE OF TmnxDot1agCfmMaMepListEntry
    MAX-ACCESS  not-accessible
    STATUS      current
    DESCRIPTION
        "The tmnxDot1agCfmMaMepListTable extends the functionality of the
         dot1agCfmMaMepListTable for the SROS series systems."
    ::= { tmnxDot1agCfmMa 3 }

tmnxDot1agCfmMaMepListEntry      OBJECT-TYPE
    SYNTAX      TmnxDot1agCfmMaMepListEntry
    MAX-ACCESS  not-accessible
    STATUS      current
    DESCRIPTION
        "The tmnxDot1agCfmMaMepListEntry augments the standard MIB entry
         for the purpose of extending functionality for the SROS series
         systems for the Dot1ag CFM MEP Lists. Rows are created and destroyed
         by the system through the row status field in dot1agCfmMaMepListEntry."
    AUGMENTS    { dot1agCfmMaMepListEntry }
    ::= { tmnxDot1agCfmMaMepListTable 1 }

TmnxDot1agCfmMaMepListEntry      ::= SEQUENCE {
    tmnxDot1agCfmMaMepListMacAddress MacAddress,
    tmnxDot1agCfmMaMepListAutoDiscvd TruthValue
}

tmnxDot1agCfmMaMepListMacAddress OBJECT-TYPE
    SYNTAX      MacAddress
    MAX-ACCESS  read-create
    STATUS      current
    DESCRIPTION
        "The value of tmnxDot1agCfmMaMepListMacAddress specifies the target
         unicast MAC address used for transmitting CFM packets to the remote
         MEPs for the specified MEPID.

         Setting a unicast MAC address restricts the number of MEPIDs that can
         be configured for an individual MA to a maximum of one (1). Setting the
         address back to the default value will remove this restriction and will
         result in the regular CCM multicast address being used. This value
         cannot be set to any multicast or broadcast address."
    DEFVAL      { '000000000000'H }
    ::= { tmnxDot1agCfmMaMepListEntry 1 }

tmnxDot1agCfmMaMepListAutoDiscvd OBJECT-TYPE
    SYNTAX      TruthValue
    MAX-ACCESS  read-create
    STATUS      current
    DESCRIPTION
      "The value of tmnxDot1agCfmMaMepListAutoDiscvd specifies whether or not
       the remote peer was automatically discovered ('true') or not.  Auto-
       discovered remote peers are created by the system only and are of a
       'volatile' storage type.  Specifying the value of 'false' will mark an
       auto-discovered remote peer as permanently configured.

       To reset a configured remote peer to auto-discovered a manager must
       destroy the corresponding dot1agCfmMaMepListEntry."
    DEFVAL { false }
    ::= { tmnxDot1agCfmMaMepListEntry 2 }

-- Nokia SROS product series CFM MepEntry table
--
-- This table is an augmentation of the dot1agCfmMepTable in IEEE8021-CFM-MIB.
--
-- Use of AUGMENTS clause implies a one-to-one dependent relationship between
-- the base table, dot1agCfmMepTable, and the augmenting table,
-- tmnxDot1agCfmMepTable, with additional columns. Creation (or deletion) of a
-- row in the dot1agCfmMepTable results in the same fate for the row in the
-- tmnxDot1agCfmMepTable.

-- ******************************************************************
-- The MEP Table
-- ******************************************************************

tmnxDot1agCfmMepTable            OBJECT-TYPE
    SYNTAX     SEQUENCE OF TmnxDot1agCfmMepEntry
    MAX-ACCESS not-accessible
    STATUS     current
    DESCRIPTION
       "This table augments the Maintenance Association End Point (MEP) table
        of the IEEE8021-CFM-MIB."
    ::= { tmnxDot1agCfmMep 1 }

tmnxDot1agCfmMepEntry            OBJECT-TYPE
    SYNTAX     TmnxDot1agCfmMepEntry
    MAX-ACCESS not-accessible
    STATUS     current
    DESCRIPTION
       "A conceptual row in the tmnxDot1agCfmMepTable. This row exists only
        if the association dot1agCfmMepEntry is active."
    AUGMENTS { dot1agCfmMepEntry }
    ::= { tmnxDot1agCfmMepTable 1 }

TmnxDot1agCfmMepEntry            ::= SEQUENCE {
    tmnxDot1agCfmMepSdpId            SdpId,
    tmnxDot1agCfmMepVcId             Unsigned32,
    tmnxDot1agCfmMepMacAddress       MacAddress,
    tmnxDot1agCfmMepAisEnable        TruthValue,
    tmnxDot1agCfmMepAisMegLevel      BITS,
    tmnxDot1agCfmMepAisPriority      Unsigned32,
    tmnxDot1agCfmMepAisInterval      Unsigned32,
    tmnxDot1agCfmMepEthRxAisInterval Unsigned32,
    tmnxDot1agCfmMepEthRxAis         TruthValue,
    tmnxDot1agCfmMepEthAisTxCount    Counter32,
    tmnxDot1agCfmMepEthTestEnable    TruthValue,
    tmnxDot1agCfmMepEthTestPattern   INTEGER,
    tmnxDot1agCfmMepEthTestMacAddr   MacAddress,
    tmnxDot1agCfmMepEthTestDataLen   Unsigned32,
    tmnxDot1agCfmMepEthTestPriority  Unsigned32,
    tmnxDot1agCfmMepOWDTMacAddress   MacAddress,
    tmnxDot1agCfmMepOWDTPriority     Unsigned32,
    tmnxDot1agCfmMepTWDTMacAddress   MacAddress,
    tmnxDot1agCfmMepTWDTPriority     Unsigned32,
    tmnxDot1agCfmMepSvcId            TmnxServId,
    tmnxDot1agCfmMepControlMep       TruthValue,
    tmnxDot1agCfmMepEthTestThreshold Unsigned32,
    tmnxDot1agCfmMepOWDTThreshold    Unsigned32,
    tmnxDot1agCfmMepFaultPropagation INTEGER,
    tmnxDot1agCfmMepFacilityIfIndex  InterfaceIndexOrZero,
    tmnxDot1agCfmMepFacilityVlanId   VlanIdOrNone,
    tmnxDot1agCfmMepFacilityType     INTEGER,
    tmnxDot1agCfmMepFcltyFaultNotify TruthValue,
    tmnxDot1agCfmMepDescription      TItemDescription,
    tmnxDot1agCfmMepMcLagInactive    INTEGER,
    tmnxDot1agCfmMepCcmPaddingSize   Unsigned32,
    tmnxDot1agCfmMepCcmIgnoreTLVs    BITS,
    tmnxDot1agCfmMepCsfEnable        TruthValue,
    tmnxDot1agCfmMepCsfRxMultiplier  Unsigned32,
    tmnxDot1agCfmMepCsfRxState       INTEGER,
    tmnxDot1agCfmMepCsfRxInterval    Unsigned32,
    tmnxDot1agCfmMepCsfRxCount       Counter32,
    tmnxDot1agCfmMepEthAisTxFail     Counter32,
    tmnxDot1agCfmMepTxLbmTimeout     Unsigned32,
    tmnxDot1agCfmMepTxLbmInterval    Unsigned32,
    tmnxDot1agCfmMepLbmPaddingSize   Unsigned32,
    tmnxDot1agCfmMepIfSupportEnable  TruthValue,
    tmnxDot1agCfmMepAisLowPrioDef    Dot1agCfmLowestAlarmPri,
    tmnxDot1agCfmMepCollectLmmStats  TruthValue,
    tmnxDot1agCfmMepCreationOrigin   TmnxCreateOrigin
}

tmnxDot1agCfmMepSdpId            OBJECT-TYPE
    SYNTAX     SdpId
    MAX-ACCESS read-create
    STATUS     current
    DESCRIPTION
       "The value of tmnxDot1agCfmMepSdpId specifies, along with the
        tmnxDot1agCfmMepVcId, the SDP-Binding within a bridge port,
        to which the MEP is attached.

        This object is applicable to SDP-Bindings only, and MUST be set
        to the null ID (0) when dot1agCfmMepIfIndex, dot1agCfmMepPrimaryVid,
        tmnxDot1agCfmMepSvcId, tmnxDot1agCfmMepFacilityIfIndex,
        tmnxDot1agCfmMepFacilityVlanId, or tmnxDot1agCfmMepFacilityType is
        non-zero. When this object is applicable (non-zero), the above objects
        MUST be set to zero (0).

        Once set, this object can not be modified."
    REFERENCE
       "802.1ag clause 12.14.2.1.2:a"
    ::= { tmnxDot1agCfmMepEntry 1 }

tmnxDot1agCfmMepVcId             OBJECT-TYPE
    SYNTAX     Unsigned32
    MAX-ACCESS read-create
    STATUS     current
    DESCRIPTION
       "The value of tmnxDot1agCfmMepVcId specifies, along with
        tmnxDot1agCfmMepSdpId, the SDP Binding for the bridge.

        tmnxDot1agCfmMepVcId is applicable to SDP-Bindings only, and MUST
        be set to zero (0) when dot1agCfmMepIfIndex, dot1agCfmMepPrimaryVid
        tmnxDot1agCfmMepSvcId, tmnxDot1agCfmMepFacilityIfIndex,
        tmnxDot1agCfmMepFacilityVlanId, or tmnxDot1agCfmMepFacilityType is
        non-zero. When this object is applicable (non-zero), the above objects
        MUST be set to zero (0).

        Once set, this object can not be modified."
    REFERENCE
       "802.1ag clause 12.14.2.1.2:d"
    ::= { tmnxDot1agCfmMepEntry 2 }

tmnxDot1agCfmMepMacAddress       OBJECT-TYPE
    SYNTAX     MacAddress
    MAX-ACCESS read-create
    STATUS     current
    DESCRIPTION
       "The value of tmnxDot1agCfmMepMacAddress specifies the mac-address
        that is assigned to dot1agCfmMepMacAddress."
    REFERENCE
      "802.1ag clause 12.14.7.1.3:i and 19.4"
    ::= { tmnxDot1agCfmMepEntry 3 }

tmnxDot1agCfmMepAisEnable        OBJECT-TYPE
    SYNTAX     TruthValue
    MAX-ACCESS read-create
    STATUS     current
    DESCRIPTION
        "The value of tmnxDot1agCfmMepAisEnable specifies whether AIS
         frames are generated from the Maintenance Entity Group (MEG)."
    DEFVAL { false }
    ::= { tmnxDot1agCfmMepEntry 4 }

tmnxDot1agCfmMepAisMegLevel      OBJECT-TYPE
    SYNTAX     BITS {
                   level1 (0),
                   level2 (1),
                   level3 (2),
                   level4 (3),
                   level5 (4),
                   level6 (5),
                   level7 (6)
               }
    MAX-ACCESS read-create
    STATUS     current
    DESCRIPTION
        "The value of tmnxDot1agCfmMepAisMegLevel specifies the levels
         that should be notified to suppress alarms resulting from defect
         conditions detected by the MEP."
    DEFVAL { { } }
    ::= { tmnxDot1agCfmMepEntry 5 }

tmnxDot1agCfmMepAisPriority      OBJECT-TYPE
    SYNTAX     Unsigned32 (0..7)
    MAX-ACCESS read-create
    STATUS     current
    DESCRIPTION
        "The value of tmnxDot1agCfmMepAisPriority specifies at what priority
         the AIS frames should be transmitted."
    DEFVAL { 7 }
    ::= { tmnxDot1agCfmMepEntry 6 }

tmnxDot1agCfmMepAisInterval      OBJECT-TYPE
    SYNTAX     Unsigned32 (1 | 60)
    UNITS      "seconds"
    MAX-ACCESS read-create
    STATUS     current
    DESCRIPTION
        "The value of tmnxDot1agCfmMepAisInterval specifies at what intervals
         to transmit AIS frames."
    DEFVAL { 1 }
    ::= { tmnxDot1agCfmMepEntry 7 }

tmnxDot1agCfmMepEthRxAisInterval OBJECT-TYPE
    SYNTAX     Unsigned32 (1 | 60)
    UNITS      "seconds"
    MAX-ACCESS read-only
    STATUS     current
    DESCRIPTION
        "The value of tmnxDot1agCfmMepEthRxAisInterval indicates the AIS
         Interval received in the last AIS Frame."
    DEFVAL { 1 }
    ::= { tmnxDot1agCfmMepEntry 8 }

tmnxDot1agCfmMepEthRxAis         OBJECT-TYPE
    SYNTAX     TruthValue
    MAX-ACCESS read-only
    STATUS     current
    DESCRIPTION
        "The value of tmnxDot1agCfmMepEthRxAis indicates the MEP is receiving
         AIS test frames from one or more of its sub-layer MEPs."
    DEFVAL { false }
    ::= { tmnxDot1agCfmMepEntry 9 }

tmnxDot1agCfmMepEthAisTxCount    OBJECT-TYPE
    SYNTAX     Counter32
    MAX-ACCESS read-only
    STATUS     current
    DESCRIPTION
        "The value of tmnxDot1agCfmMepEthAisTxCount indicates number of
         AIS frames transmitted on the MEP."
    ::= { tmnxDot1agCfmMepEntry 10 }

tmnxDot1agCfmMepEthTestEnable    OBJECT-TYPE
    SYNTAX     TruthValue
    MAX-ACCESS read-create
    STATUS     current
    DESCRIPTION
        "The value of tmnxDot1agCfmMepEthTestEnable specifies whether
         Ethernet test frames are to be generated on transmission or
         processed on reception. If this object is set to 'false',
         then tmnxDot1agCfmMepEthTestPattern is undefined.

         When this object is set to 'true', tmnxDot1agCfmMepEthTestPattern
         is reset to its default value, unless tmnxDot1agCfmMepEthTestPattern
         is set to a specific value in the same SNMP PDU."
    DEFVAL { false }
    ::= { tmnxDot1agCfmMepEntry 11 }

tmnxDot1agCfmMepEthTestPattern   OBJECT-TYPE
    SYNTAX     INTEGER {
                   allZerosNoCrc  (0),
                   allZerosCrc    (1),
                   prbsNoCrc      (2),
                   prbsCrc        (3),
                   allOnesNoCrc   (4),
                   allOnesCrc     (5)
               }
    MAX-ACCESS read-create
    STATUS     current
    DESCRIPTION
        "The value of tmnxDot1agCfmMepEthTestPattern specifies the data-content
         of the AIS test frames. 'allZerosNoCrc (0)' and 'allZerosCrc (1)'
         specifies the data content as all zero values (without and with CRC
         calculations respectively). 'prbsNoCrc (3) and 'prbsCrc (4) specifies
         the data content as pseudo random bit sequence (without and with CRC
         calculations respectively). 'allOnesNoCrc (4)' and 'allOnesCrc (5)',
         specifies the data content as all ones (without and with CRC
         calculations respectively).

         This object is only applicable if tmnxDot1agCfmMepEthTestEnable is set
         to 'true'."
    DEFVAL { allZerosNoCrc }
    ::= { tmnxDot1agCfmMepEntry 12 }

tmnxDot1agCfmMepEthTestMacAddr   OBJECT-TYPE
    SYNTAX     MacAddress
    MAX-ACCESS read-create
    STATUS     current
    DESCRIPTION
        "The value of tmnxDot1agCfmMepEthTestMacAddr specifies the MAC address
         of the target to whom the Eth-test frames are sent.

         Setting this object will trigger the test frame to be sent. Once the
         test is complete, the object will revert to the default value,
         indicating that another test is possible."
    DEFVAL { '000000000000'H }
    ::= { tmnxDot1agCfmMepEntry 13 }

tmnxDot1agCfmMepEthTestDataLen   OBJECT-TYPE
    SYNTAX     Unsigned32 (64..1500)
    MAX-ACCESS read-create
    STATUS     current
    DESCRIPTION
        "The value of tmnxDot1agCfmMepEthTestDataLen specifies the length of the
         data sent in an Eth-test frame. The contents of the data is specified
         by the tmnxDot1agCfmMepEthTestPattern object."
    DEFVAL { 64 }
    ::= { tmnxDot1agCfmMepEntry 14 }

tmnxDot1agCfmMepEthTestPriority  OBJECT-TYPE
    SYNTAX     Unsigned32 (0..7)
    MAX-ACCESS read-create
    STATUS     current
    DESCRIPTION
        "The value of tmnxDot1agCfmMepEthTestPriority specifies the priority
         used in generating Eth-Test frames."
    DEFVAL { 7 }
    ::= { tmnxDot1agCfmMepEntry 15 }

tmnxDot1agCfmMepOWDTMacAddress   OBJECT-TYPE
    SYNTAX     MacAddress
    MAX-ACCESS read-create
    STATUS     current
    DESCRIPTION
        "The value of tmnxDot1agCfmMepOWDTMacAddress specifies the MAC address
         used as a target for the One-Way-Delay Test (OWDT).

         Setting this object will trigger a One-Way-Delay test to the specified
         MAC address.

         Upon completion of the test, the MacAddress will revert to its default
         value, indicating that another test is possible."
    DEFVAL { '000000000000'H }
    ::= { tmnxDot1agCfmMepEntry 16 }

tmnxDot1agCfmMepOWDTPriority     OBJECT-TYPE
    SYNTAX     Unsigned32 (0..7)
    MAX-ACCESS read-create
    STATUS     current
    DESCRIPTION
        "The value of tmnxDot1agCfmMepOWDTPriority specifies the priority used
         in the generated test frame for the One-Way-Delay test."
    DEFVAL { 7 }
    ::= { tmnxDot1agCfmMepEntry 17 }

tmnxDot1agCfmMepTWDTMacAddress   OBJECT-TYPE
    SYNTAX     MacAddress
    MAX-ACCESS read-create
    STATUS     current
    DESCRIPTION
        "The value of tmnxDot1agCfmMepTWDTMacAddress specifies the MAC address
         used as a target for the Two-Way-Delay Test (TWDT).

         Setting this object will trigger a Two-Way-Delay test to the specified
         MAC address.

         Upon completion of the test, the MacAddress will revert to its default
         value, indicating that another test is possible."
    DEFVAL { '000000000000'H }
    ::= { tmnxDot1agCfmMepEntry 18 }

tmnxDot1agCfmMepTWDTPriority     OBJECT-TYPE
    SYNTAX     Unsigned32 (0..7)
    MAX-ACCESS read-create
    STATUS     current
    DESCRIPTION
        "The value of tmnxDot1agCfmMepTWDTPriority specifies the priority used
         in the generated test frame for the Two-Way-Delay test."
    DEFVAL { 7 }
    ::= { tmnxDot1agCfmMepEntry 19 }

tmnxDot1agCfmMepSvcId            OBJECT-TYPE
    SYNTAX     TmnxServId
    MAX-ACCESS read-create
    STATUS     current
    DESCRIPTION
       "The value of tmnxDot1agCfmMepSvcId specifies the service to which the
        virtual MEP is attached.

        tmnxDot1agCfmMepSvcId is applicable to virtual MEPs only, and MUST
        be set to zero (0) when dot1agCfmMepIfIndex, dot1agCfmMepPrimaryVid,
        tmnxDot1agCfmMepSdpId, tmnxDot1agCfmMepVcId,
        tmnxDot1agCfmMepFacilityIfIndex, tmnxDot1agCfmMepFacilityVlanId, or
        tmnxDot1agCfmMepFacilityType is non-zero.  When this object is
        applicable (non-zero), the above objects MUST be set to zero (0).

        Once set, this object can not be modified."
    ::= { tmnxDot1agCfmMepEntry 20 }

tmnxDot1agCfmMepControlMep       OBJECT-TYPE
    SYNTAX      TruthValue
    MAX-ACCESS  read-create
    STATUS      current
    DESCRIPTION
        "The value of tmnxDot1agCfmMepControlMep specifies whether or not the
         operational state of the MEP is used by the management entity over
         which this MEP is configured."
    DEFVAL { false }
    ::= { tmnxDot1agCfmMepEntry 21 }

tmnxDot1agCfmMepEthTestThreshold OBJECT-TYPE
    SYNTAX      Unsigned32 (0..11840)
    UNITS       "bit-errors"
    MAX-ACCESS  read-create
    STATUS      current
    DESCRIPTION
        "The value of tmnxDot1agCfmMepEthTestThreshold specifies when a
         tmnxDot1agCfmMepEthTestComplete notification is sent. If
         tmnxDot1agCfmMepEthTestThreshold is set to zero (0), a notification is
         sent on the completion of any test for this MEP. Otherwise the
         threshold must be exceeded and/or CRC failures must be detected to
         send the notification."
    DEFVAL { 1 }
    ::= { tmnxDot1agCfmMepEntry 22 }

tmnxDot1agCfmMepOWDTThreshold    OBJECT-TYPE
    SYNTAX       Unsigned32 (0..600)
    UNITS        "seconds"
    MAX-ACCESS   read-create
    STATUS       current
    DESCRIPTION
        "The value of tmnxDot1agCfmMepOWDTThreshold specifies when a
         tmnxDot1agCfmMepDMTestComplete notification is sent for a one-way-delay
         test. If tmnxDot1agCfmMepOWDTThreshold is set to zero (0), a
         notification is sent on the completion of any one-way-delay-test for
         this MEP. Otherwise the threshold must be exceeded to send the
         notification."
    DEFVAL { 3 }
    ::= { tmnxDot1agCfmMepEntry 23 }

tmnxDot1agCfmMepFaultPropagation OBJECT-TYPE
    SYNTAX     INTEGER {
                    disabled       (0),
                    useIfStatusTLV (1),
                    suspendCCM     (2)
                }
    MAX-ACCESS read-create
    STATUS     current
    DESCRIPTION
        "The value of tmnxDot1agCfmMepFaultPropagation specifies what action
         should be taken by the MEP if a fault is detected in the service
         containing the MEP.  It also specifies if the MEP should propagate
         a fault that it has detected into the service.

         When this object is set to 'disabled (0)', no additional fault
         propagation will occur.  When this object is set to 'useIfStatusTLV
         (1)', the MEP will send an interface status TLV in the next CCM
         indicating fault when fault is detected, even if the MEP itself has
         not detected a fault.  When this object is set to 'suspendCCM (2)',
         faults will be propagated by stopping the regular CCM transmissions
         entirely.  Once the fault is cleared, the regular CCM transmissions
         will resume.  Additionally, when the value of
         tmnxDot1agCfmMepFaultPropagation is different than 'disabled (0)', a
         defect detected by the MEP will be propagated into the service."
    DEFVAL { disabled }
    ::= { tmnxDot1agCfmMepEntry 24 }

tmnxDot1agCfmMepFacilityIfIndex  OBJECT-TYPE
    SYNTAX      InterfaceIndexOrZero
    MAX-ACCESS  read-create
    STATUS      current
    DESCRIPTION
        "The value of tmnxDot1agCfmMepFacilityIfIndex specifies, along with
         tmnxDot1agCfmMepFacilityVlanId and tmnxDot1agCfmMepFacilityType,
         the port or interface associated with this MEP.

         The tmnxDot1agCfmMepFacilityIfIndex is applicable to facility MEPs
         only, and MUST be set to zero (0) when dot1agCfmMepIfIndex,
         dot1agCfmMepPrimaryVid, tmnxDot1agCfmMepSdpId, tmnxDot1agCfmMepVcId,
         or tmnxDot1agCfmMepSvcId is non-zero. When this object is applicable
         (non-zero), the above objects MUST be set to zero (0).

         Once set, this object can not be modified."
    DEFVAL { 0 }
    ::= { tmnxDot1agCfmMepEntry 25 }

tmnxDot1agCfmMepFacilityVlanId   OBJECT-TYPE
    SYNTAX      VlanIdOrNone
    MAX-ACCESS  read-create
    STATUS      current
    DESCRIPTION
        "The value of tmnxDot1agCfmMepFacilityVlanId specifies, along with
         tmnxDot1agCfmMepFacilityIfIndex and tmnxDot1agCfmMepFacilityType,
         the encapsulation value of the port or interface
         associated with this MEP.

         The tmnxDot1agCfmMepFacilityVlanId is applicable to facility MEPs only,
         and MUST be set to zero (0) when dot1agCfmMepIfIndex,
         dot1agCfmMepPrimaryVid, tmnxDot1agCfmMepSdpId, tmnxDot1agCfmMepVcId,
         or tmnxDot1agCfmMepSvcId is non-zero. When this object is applicable
         (non-zero), the above objects MUST be set to zero (0).

         Once set, this object can not be modified."
    DEFVAL { 0 }
    ::= { tmnxDot1agCfmMepEntry 26 }

tmnxDot1agCfmMepFacilityType     OBJECT-TYPE
    SYNTAX      INTEGER {
                    nonFacilityType (0),
                    port            (1),
                    interface       (2)
                }
    MAX-ACCESS  read-create
    STATUS      current
    DESCRIPTION
        "The value of tmnxDot1agCfmMepFacilityType specifies, along with
         tmnxDot1agCfmMepFacilityIfIndex and tmnxDot1agCfmMepFacilityVlanId,
         whether the port or interface is associated with this MEP.

         The tmnxDot1agCfmMepFacilityType is applicable to facility MEPs only,
         and MUST be set to 'nonFacilityType (0)' when dot1agCfmMepIfIndex,
         dot1agCfmMepPrimaryVid, tmnxDot1agCfmMepSdpId, tmnxDot1agCfmMepVcId,
         or tmnxDot1agCfmMepSvcId is non-zero. When this object is applicable
         (non-zero), the above objects MUST be set to zero (0).

         Once set, this object can not be modified."
    DEFVAL { nonFacilityType }
    ::= { tmnxDot1agCfmMepEntry 27 }

tmnxDot1agCfmMepFcltyFaultNotify OBJECT-TYPE
    SYNTAX      TruthValue
    MAX-ACCESS  read-create
    STATUS      current
    DESCRIPTION
        "The value of tmnxDot1agCfmMepFcltyFaultNotify specifies whether or not
         a fault detected on this Facility MEP will notify the port or facility
         tunnel associated to this MEP.

         This object pertains to Facility MEPs only. Attempting to change this
         object away from its default for a non-facility MEP will result in an
         'inconsistentValue' error."
    DEFVAL { false }
    ::= { tmnxDot1agCfmMepEntry 28 }

tmnxDot1agCfmMepDescription      OBJECT-TYPE
    SYNTAX      TItemDescription
    MAX-ACCESS  read-create
    STATUS      current
    DESCRIPTION
        "The value of tmnxDot1agCfmMepDescription specifies a user supplied
         detailed description for this ETH-CFM MEP."
    DEFVAL      { "" }
    ::= { tmnxDot1agCfmMepEntry 29 }

tmnxDot1agCfmMepMcLagInactive    OBJECT-TYPE
    SYNTAX      INTEGER {
                    notApplicable (0),
                    standby       (1),
                    active        (2)
                }
    MAX-ACCESS  read-only
    STATUS      current
    DESCRIPTION
        "The value of tmnxDot1agCfmMepMcLagInactive indicates whether or not the
         MEP is inactive, 'standby (2)', due to the MC-LAG standby state.  The
         value of tmnxDot1agCfmMcLagStdbyInactive must be set to 'true (1)' for
         this object to have meaning and return anything other than
         'notApplicable (0)'."
    ::= { tmnxDot1agCfmMepEntry 30 }

tmnxDot1agCfmMepCcmPaddingSize   OBJECT-TYPE
    SYNTAX      Unsigned32 (0|3..1500)
    MAX-ACCESS  read-create
    STATUS      current
    DESCRIPTION
        "The value of tmnxDot1agCfmMepCcmPaddingSize specifies the number of
         additional octets inserted into the CCM PDU for the Data TLV padding.
         If tmnxDot1agCfmMepCcmPaddingSize is set to zero (0), no Data TLV will
         be added to the CCM PDUs."
    DEFVAL { 0 }
    ::= { tmnxDot1agCfmMepEntry 31 }

tmnxDot1agCfmMepCcmIgnoreTLVs    OBJECT-TYPE
    SYNTAX      BITS {
                    interfaceStatus   (0),
                    portStatus        (1)
                }
    MAX-ACCESS  read-create
    STATUS      current
    DESCRIPTION
        "The value of tmnxDot1agCfmMepCcmIgnoreTLVs specifies the set of TLVs
         that are received in a CCM PDU for the Remote MEP state machine of the
         MEP that will be validated for format correctness but their values will
         be ignored and marked 'Absent' by ETH-CFM."
    DEFVAL { { } }
    ::= { tmnxDot1agCfmMepEntry 32 }

tmnxDot1agCfmMepCsfEnable        OBJECT-TYPE
    SYNTAX      TruthValue
    MAX-ACCESS  read-create
    STATUS      current
    DESCRIPTION
        "The value of tmnxDot1agCfmMepCsfEnable specifies whether received CSF
         (Client Signal Fault) frames are processed by the Maintenance Entity
         Group (MEG)."
    DEFVAL { false }
    ::= { tmnxDot1agCfmMepEntry 33 }

tmnxDot1agCfmMepCsfRxMultiplier  OBJECT-TYPE
    SYNTAX      Unsigned32 (0|20..300)
    MAX-ACCESS  read-create
    STATUS      current
    DESCRIPTION
        "The value of tmnxDot1agCfmMepCsfRxMultiplier specifies the receive
         period multiplier used for timing out CSF, in increments of 5.

         To calculate the timeout period of CSF frames the following formula is
         used:

             (CSF-rx-interval X multiplier) / 10

         The default multiplier, therefore, is 3.5 times the interval."
    DEFVAL { 35 }
    ::= { tmnxDot1agCfmMepEntry 34 }

tmnxDot1agCfmMepCsfRxState       OBJECT-TYPE
    SYNTAX      INTEGER {
                    los     (0),
                    ais     (1),
                    rdi     (2),
                    dci     (3)
                }
    MAX-ACCESS  read-only
    STATUS      current
    DESCRIPTION
        "The value of tmnxDot1agCfmMepCsfRxState indicates the state of the
         received CSF frames for the MEP.
         The values are:
             los (0) - Client Loss of Signal
             ais (1) - Client Forward Defect Indication
             rdi (2) - Client Reverse Defect Indication
             dci (3) - Client Defect Clear Indication"
    DEFVAL { dci }
    ::= { tmnxDot1agCfmMepEntry 35 }

tmnxDot1agCfmMepCsfRxInterval    OBJECT-TYPE
    SYNTAX      Unsigned32 (1 | 60)
    UNITS       "seconds"
    MAX-ACCESS  read-only
    STATUS      current
    DESCRIPTION
        "The value of tmnxDot1agCfmMepCsfRxInterval indicates the CSF Interval
         received in the most recent CSF frame."
    DEFVAL { 1 }
    ::= { tmnxDot1agCfmMepEntry 36 }

tmnxDot1agCfmMepCsfRxCount       OBJECT-TYPE
    SYNTAX      Counter32
    MAX-ACCESS  read-only
    STATUS      current
    DESCRIPTION
        "The value of tmnxDot1agCfmMepCsfRxCount indicates the number of CSF
         frames received on the MEP since the time CSF was enabled."
    ::= { tmnxDot1agCfmMepEntry 37 }

tmnxDot1agCfmMepEthAisTxFail     OBJECT-TYPE
    SYNTAX     Counter32
    MAX-ACCESS read-only
    STATUS     current
    DESCRIPTION
        "The value of tmnxDot1agCfmMepEthAisTxFail indicates the number of
         AIS frames the MEP failed to transmit due to resource limitations."
    ::= { tmnxDot1agCfmMepEntry 38 }

tmnxDot1agCfmMepTxLbmTimeout     OBJECT-TYPE
    SYNTAX     Unsigned32 (1..10)
    UNITS       "seconds"
    MAX-ACCESS  read-create
    STATUS     current
    DESCRIPTION
        "The value of tmnxDot1agCfmMepTxLbmTimeout specifies the duration,
         in seconds, before a loopback PDU sent by the node is considered to be
         timed out."
    DEFVAL { 5 }
    ::= { tmnxDot1agCfmMepEntry 39 }

tmnxDot1agCfmMepTxLbmInterval    OBJECT-TYPE
    SYNTAX     Unsigned32 (0|1..600)
    UNITS       "centiseconds"
    MAX-ACCESS  read-create
    STATUS     current
    DESCRIPTION
        "The value of tmnxDot1agCfmMepTxLbmInterval specifies the duration,
         in centiseconds, between loopback PDU transmissions.  A value of zero
         is only valid if there are 5 or fewer loopbacks in the test (as defined
         by dot1agCfmMepTransmitLbmMessages)."
    DEFVAL { 0 }
    ::= { tmnxDot1agCfmMepEntry 40 }

tmnxDot1agCfmMepLbmPaddingSize   OBJECT-TYPE
    SYNTAX      Unsigned32 (0|3..9000)
    MAX-ACCESS  read-create
    STATUS      current
    DESCRIPTION
        "The value of tmnxDot1agCfmMepLbmPaddingSize specifies the number of
         additional octets inserted into the LBM PDU for the Data TLV padding.
         If tmnxDot1agCfmMepLbmPaddingSize is set to zero (0), no Data TLV will
         be added to the LBM PDUs.  Note that setting this value is mutually
         exclusive with setting dot1agCfmMepTransmitLbmDataTlv."
    DEFVAL { 0 }
    ::= { tmnxDot1agCfmMepEntry 41 }

tmnxDot1agCfmMepIfSupportEnable  OBJECT-TYPE
    SYNTAX      TruthValue
    MAX-ACCESS  read-create
    STATUS      current
    DESCRIPTION
        "The value of tmnxDot1agCfmMepIfSupportEnable specifies whether or not
         the MEP will generate AIS PDUs when the endpoint associated to this MEP
         is down regardless of CCM failures."
    DEFVAL { false }
    ::= { tmnxDot1agCfmMepEntry 42 }

tmnxDot1agCfmMepAisLowPrioDef    OBJECT-TYPE
    SYNTAX      Dot1agCfmLowestAlarmPri
    MAX-ACCESS  read-create
    STATUS      current
    DESCRIPTION
        "The value of tmnxDot1agCfmMepAisLowPrioDef specifies the lowest
         priority defect that is allowed to generate an AIS frame.

         When this object is 'allDef (1)', AIS frame generation will be
         triggered for any defect in the CCM state machine.

         When this object is 'macRemErrXcon (2)', AIS frame generation will be
         triggered for defMACstatus defect and any defect higher than
         defMACstatus."
    DEFVAL { allDef }
    ::= { tmnxDot1agCfmMepEntry 43 }

tmnxDot1agCfmMepCollectLmmStats  OBJECT-TYPE
    SYNTAX      TruthValue
    MAX-ACCESS  read-create
    STATUS      current
    DESCRIPTION
        "The value of tmnxDot1agCfmMepCollectLmmStats specifies whether or not
         to compute the Y.1731 Ethernet Loss Measurement (ETH-LM) 'RxFCl' and
         'TxFCl' service frame counters for the specified MEP.  The 'RxFCl' and
         'TxFCl' counters are used by ETH-LM tests.  An ETH-LM test is created
         using TIMETRA-OAM-PM-MIB::tmnxOamPmCfgLossLmmRowStatus."
    REFERENCE
        "ITU-T G.8013/Y.1731, 'OAM functions and mechanisms for Ethernet based
         networks', 11/2013, Section 8.1 'Frame loss measurement (ETH-LM)'."
    DEFVAL { false }
    ::= { tmnxDot1agCfmMepEntry 44 }

tmnxDot1agCfmMepCreationOrigin  OBJECT-TYPE
    SYNTAX      TmnxCreateOrigin
    MAX-ACCESS  read-only
    STATUS      current
    DESCRIPTION
     "The value of tmnxDot1agCfmMepCreationOrigin indicates the
      mechanism which created this entry."
    ::= { tmnxDot1agCfmMepEntry 45 }

-- Nokia SROS product series CFM Global Objects
--
-- The Global Configuration for Ethernet CFM.
--

tmnxDot1agCfmMcLagConfigGroup  OBJECT IDENTIFIER ::= {tmnxDot1agCfmGlobalObjs 1}

-- ******************************************************************
-- The Multi-Chassis LAG Configuration Objects
-- ******************************************************************

tmnxDot1agCfmMcLagStdbyInactive  OBJECT-TYPE
    SYNTAX      TruthValue
    MAX-ACCESS  read-write
    STATUS      current
    DESCRIPTION
         "The value of tmnxDot1agCfmMcLagStdbyInactive specifies whether or not
          ETH-CFM MEPs configured on Multi-Chassis LAG ports are aware of MC-LAG
          port active/standby states.

          When this object is 'true (1)', MEPs configured on a Multi-Chassis
          LAG port will act as if they are administratively shutdown if running
          on a standby port, and will only be operational on an active MC-LAG
          port.

          When this object is 'false (2)', MEPs configured on a Multi-Chassis
          LAG port will operate regardless of the MC-LAG port active and standby
          states."
    DEFVAL { false }
    ::= { tmnxDot1agCfmMcLagConfigGroup 1 }

tmnxDot1agCfmMcLagPropHoldTime   OBJECT-TYPE
    SYNTAX      Unsigned32 (0..60)
    UNITS       "seconds"
    MAX-ACCESS  read-write
    STATUS      current
    DESCRIPTION
        "The value of tmnxDot1agCfmMcLagPropHoldTime specifies the duration, in
         seconds, of a timer that is activated when an MC-LAG port or protocol
         changes state. While the timer is active, no fault set or clear is
         propagated to the MC-LAG SAP's CFM MEP.

         The outstanding hold time can be monitored by polling the value of
         sapEthCfmMcLagPropHoldTimeRemain for a particular SAP.  When set to
         the value zero (0), no delay in response to a port or protocol change
         will be observed.

         This object is meaningful only when tmnxDot1agCfmMcLagStdbyInactive is
         set to the value 'enabled (1)', otherwise an SNMP Set operation will
         result in an inconsistentValue error and the result of an SNMP Get
         operation will be undefined."
    DEFVAL { 1 }
    ::= { tmnxDot1agCfmMcLagConfigGroup 2 }

-- ******************************************************************
-- The Synthetic Loss Measurement Configuration Objects
-- ******************************************************************
tmnxDot1agCfmSLMConfigGroup  OBJECT IDENTIFIER ::= {tmnxDot1agCfmGlobalObjs 2}

tmnxDot1agCfmSLMInactivityTimer  OBJECT-TYPE
    SYNTAX      Unsigned32 (10..100)
    UNITS       "seconds"
    MAX-ACCESS  read-write
    STATUS      current
    DESCRIPTION
        "The value of tmnxDot1agCfmSLMInactivityTimer specifies the duration,
         in seconds, that the system will maintain Synthetic Loss Measurement
         (SLM) reply (SLR) data for individual two-way tests in the absence of
         receiving SLM frames.

         The system may be blocked in responding to new two-way SLM tests due to
         an excessive inactive timer duration. In this case, reducing this
         object's value, thus reducing the retention time for existing latent
         SLR test data, will help free test resources allowing the system to
         respond to new two-way SLM tests."
    REFERENCE "ITU-T Y.1731 Ethernet Synthetic Frame Loss Measurement (ETH-SLM)
               Section 8.2 Note 2."
    DEFVAL {  100 }
    ::= { tmnxDot1agCfmSLMConfigGroup 1 }

-- ******************************************************************
-- Global ETH-CFM Statistics Objects
-- ******************************************************************
tmnxDot1agCfmStatisticsGroup  OBJECT IDENTIFIER ::= {tmnxDot1agCfmGlobalObjs 3}

tmnxDot1agCfmGlobalPacketStats   OBJECT IDENTIFIER ::=
                                               {tmnxDot1agCfmStatisticsGroup 1}

tmnxDot1agCfmGlobalPacketRxCount OBJECT-TYPE
    SYNTAX      Counter32
    UNITS       "packets"
    MAX-ACCESS  read-only
    STATUS      current
    DESCRIPTION
        "The value of tmnxDot1agCfmGlobalPacketRxCount indicates the number of
         received ETH-CFM packets."
    ::= { tmnxDot1agCfmGlobalPacketStats 1 }

tmnxDot1agCfmGlobalPacketTxCount OBJECT-TYPE
    SYNTAX      Counter32
    UNITS       "packets"
    MAX-ACCESS  read-only
    STATUS      current
    DESCRIPTION
        "The value of tmnxDot1agCfmGlobalPacketTxCount indicates the number of
         transmitted ETH-CFM packets."
    ::= { tmnxDot1agCfmGlobalPacketStats 2 }

tmnxDot1agCfmGlobalPacketDropped OBJECT-TYPE
    SYNTAX      Counter32
    UNITS       "packets"
    MAX-ACCESS  read-only
    STATUS      current
    DESCRIPTION
        "The value of tmnxDot1agCfmGlobalPacketDropped indicates the number of
         packets dropped by ETH-CFM. A packet is dropped because of resource
         contention."
    ::= { tmnxDot1agCfmGlobalPacketStats 3 }

tmnxDot1agCfmGlobalPacketDiscard OBJECT-TYPE
    SYNTAX      Counter32
    UNITS       "packets"
    MAX-ACCESS  read-only
    STATUS      current
    DESCRIPTION
        "The value of tmnxDot1agCfmGlobalPacketDiscard indicates the number of
         packets discarded by ETH-CFM. A packet may be discarded for several
         reasons including, but not limited to, malformed PDU, invalid TLVs,
         MEP admin down, etc."
    ::= { tmnxDot1agCfmGlobalPacketStats 4 }

tmnxDot1agCfmGlobalAisTxActive   OBJECT-TYPE
    SYNTAX      Counter32
    UNITS       "sessions"
    MAX-ACCESS  read-only
    STATUS      current
    DESCRIPTION
        "The value of tmnxDot1agCfmGlobalAisTxActive indicates the number of
         sessions where fault (AIS or other) is actively being transmitted."
    ::= { tmnxDot1agCfmGlobalPacketStats 5 }

tmnxDot1agCfmGlobalAisTxFail     OBJECT-TYPE
    SYNTAX      Counter32
    UNITS       "sessions"
    MAX-ACCESS  read-only
    STATUS      current
    DESCRIPTION
        "The value of tmnxDot1agCfmGlobalAisTxFail indicates the number of
         sessions where fault (AIS or other) can't be transmitted due to lack of
         resources."
    ::= { tmnxDot1agCfmGlobalPacketStats 6 }

--
-- Nokia SROS product series dot1ag CFM Resource Limit Table
--
-- The CFM Component (Resource) Limit Table
tmnxDot1agCfmComponentLimitTable OBJECT-TYPE
    SYNTAX      SEQUENCE OF TmnxDot1agCfmComponentLimitEntry
    MAX-ACCESS  not-accessible
    STATUS      current
    DESCRIPTION
        "The tmnxDot1agCfmComponentLimitTable stores the current resource counts
         as well as their resource limits for Ethernet Connectivity Fault
         Management (ETH-CFM) components in the SROS series system."
    ::= { tmnxDot1agCfmStatisticsGroup 2 }

tmnxDot1agCfmComponentLimitEntry OBJECT-TYPE
    SYNTAX      TmnxDot1agCfmComponentLimitEntry
    MAX-ACCESS  not-accessible
    STATUS      current
    DESCRIPTION
        "The tmnxDot1agCfmComponentLimitEntry consists of the resource limits
        for a particular component of ETH-CFM.

        Rows are managed by the system and can not be created or destroyed using
        SNMP set requests."
    INDEX { tmnxDot1agCfmCompMajorIndex,
            tmnxDot1agCfmCompMinorIndex
          }
    ::= { tmnxDot1agCfmComponentLimitTable 1 }

TmnxDot1agCfmComponentLimitEntry ::= SEQUENCE {
    tmnxDot1agCfmCompMajorIndex      Unsigned32,
    tmnxDot1agCfmCompMinorIndex      Unsigned32,
    tmnxDot1agCfmCompName            TNamedItem,
    tmnxDot1agCfmCompResourceUsage   Unsigned32,
    tmnxDot1agCfmCompResourceLimit   Unsigned32
}

tmnxDot1agCfmCompMajorIndex      OBJECT-TYPE
    SYNTAX      Unsigned32
    MAX-ACCESS  not-accessible
    STATUS      current
    DESCRIPTION
        "The value of tmnxDot1agCfmCompMajorIndex specifies the major identifier
         of the ETH-CFM component."
    ::= { tmnxDot1agCfmComponentLimitEntry 1 }

tmnxDot1agCfmCompMinorIndex      OBJECT-TYPE
    SYNTAX      Unsigned32
    MAX-ACCESS  not-accessible
    STATUS      current
    DESCRIPTION
        "The value of tmnxDot1agCfmCompMinorIndex specifies the minor identifier
         of the ETH-CFM component."
    ::= { tmnxDot1agCfmComponentLimitEntry 2 }

tmnxDot1agCfmCompName            OBJECT-TYPE
    SYNTAX      TNamedItem
    MAX-ACCESS  read-only
    STATUS      current
    DESCRIPTION
        "The value of tmnxDot1agCfmCompName indicates the name of the ETH-CFM
         component."
    ::= { tmnxDot1agCfmComponentLimitEntry 3 }

tmnxDot1agCfmCompResourceUsage   OBJECT-TYPE
    SYNTAX      Unsigned32
    MAX-ACCESS  read-only
    STATUS      current
    DESCRIPTION
        "The value of tmnxDot1agCfmCompResourceUsage indicates the current
         resource usage for the ETH-CFM component."
    ::= { tmnxDot1agCfmComponentLimitEntry 4 }

tmnxDot1agCfmCompResourceLimit   OBJECT-TYPE
    SYNTAX      Unsigned32
    MAX-ACCESS  read-only
    STATUS      current
    DESCRIPTION
        "The value of tmnxDot1agCfmCompResourceLimit indicates the maximum
         resource usage limit for the ETH-CFM component for the
         SROS series system."
    ::= { tmnxDot1agCfmComponentLimitEntry 5 }

-- ******************************************************************
-- Global ETH-CFM MEP Objects
-- ******************************************************************
tmnxDot1agCfmSystemScalarsGroup
                               OBJECT IDENTIFIER ::= {tmnxDot1agCfmGlobalObjs 4}

tmnxDot1agCfmGraceTxEnable       OBJECT-TYPE
    SYNTAX      TruthValue
    MAX-ACCESS  read-write
    STATUS      current
    DESCRIPTION
         "The value of tmnxDot1agCfmGraceTxEnable specifies whether or not grace
          period notifications will be sent to the ETH-CFM remote MEP peers. The
          value 'true' enables grace period notifications, and the value 'false'
          suppresses the notifications.

          During an outage, the modification of this object from 'true' to
          'false' will cause an immediate clear of all grace period
          notifications, after which no further notifications will be sent. A
          modification of this object from 'false' to 'true' will not enable the
          transmission of grace period for any outages currently in progress but
          will take effect for subsequent outages."
    DEFVAL { true }
    ::= { tmnxDot1agCfmSystemScalarsGroup 1 }

tmnxDot1agCfmGracePeriod         OBJECT-TYPE
    SYNTAX      TruthValue
    MAX-ACCESS  read-only
    STATUS      current
    DESCRIPTION
         "The value of tmnxDot1agCfmGracePeriod indicates whether or not the
          node is locally executing a grace period.  A value of 'true' indicates
          that all peer timeouts are extended locally and eligible MEPs are
          transmitting grace period information.  A value of 'false' indicates
          no grace period information is transmitted and standard values are
          used for timing out remote peers.

          Note that for a local MEP to be eligible for grace period transmission
          it must be admin up and ccm-enabled.  Additionally, for any
          transmission to occur tmnxDot1agCfmGraceTxEnable must be set to
          'true'."
    ::= { tmnxDot1agCfmSystemScalarsGroup 2 }

tmnxDot1agCfmSenderIdType        OBJECT-TYPE
    SYNTAX      LldpChassisIdSubtype
    MAX-ACCESS  read-write
    STATUS      current
    DESCRIPTION
        "The value of tmnxDot1agCfmSenderIdType specifies the type of sender
         identification that is transmitted in CFM PDUs generated from this
         system.

         The value of 'chassisComponent (1)' indicates that the system's name
         (TIMETRA-CHASSIS-MIB::tmnxChassisName) is inserted in transmitted
         PDUs, while 'local (7)' indicates that the value as defined in
         tmnxDot1agCfmSenderIdName is transmitted."
    DEFVAL      { chassisComponent }
    ::= { tmnxDot1agCfmSystemScalarsGroup 3 }

tmnxDot1agCfmSenderIdName        OBJECT-TYPE
    SYNTAX      OCTET STRING (SIZE (0..45))
    MAX-ACCESS  read-write
    STATUS      current
    DESCRIPTION
        "The value of tmnxDot1agCfmSenderIdName specifies the locally defined
         sender-id name that is inserted in all CFM transmitted PDUs.  The value
         of this object is only meaningful if the value of
         tmnxDot1agCfmSenderIdType is set to the value 'local (7)'. Otherwise
         the value of this object MUST be the empty string.

         The value of this object MUST be set to a non-empty string in the same
         SNMP PDU as the modification of tmnxDot1agCfmSenderIdType when the type
         is assigned to the value 'local (7)'. Modification of the type away
         from 'local (7)' will automatically reset the value to its default
         value."
    DEFVAL      { "" }
    ::= { tmnxDot1agCfmSystemScalarsGroup 4 }

--
-- Global ETH-CFM Per Opcode Statistics Table
--
tmnxDot1agCfmGlobalOpcodeTable   OBJECT-TYPE
    SYNTAX      SEQUENCE OF TmnxDot1agCfmGlobalOpcodeEntry
    MAX-ACCESS  not-accessible
    STATUS      current
    DESCRIPTION
       "tmnxDot1agCfmGlobalOpcodeTable consists of global statistics that
        are kept in the receive and transmit direction on the node for each
        CFM PDU Opcode."
    REFERENCE
       "Y.1731 clauses 8 and 9"
    ::= { tmnxDot1agCfmStatisticsGroup 3 }

tmnxDot1agCfmGlobalOpcodeEntry   OBJECT-TYPE
    SYNTAX      TmnxDot1agCfmGlobalOpcodeEntry
    MAX-ACCESS  not-accessible
    STATUS      current
    DESCRIPTION
       "A Global Opcode Stats Table entry."
    INDEX { tmnxDot1agCfmGlobalOpcode }
    ::= { tmnxDot1agCfmGlobalOpcodeTable 1 }

TmnxDot1agCfmGlobalOpcodeEntry   ::= SEQUENCE {
      tmnxDot1agCfmGlobalOpcode            Dot1agCfmStatisticOpcodeName,
      tmnxDot1agCfmGlobalOpcodeRx          Counter32,
      tmnxDot1agCfmGlobalOpcodeTx          Counter32
    }

tmnxDot1agCfmGlobalOpcode        OBJECT-TYPE
    SYNTAX Dot1agCfmStatisticOpcodeName
    MAX-ACCESS  not-accessible
    STATUS      current
    DESCRIPTION
       "Integer that defines which CFM PDU Opcode the statistics refer to."
    ::= { tmnxDot1agCfmGlobalOpcodeEntry 1 }

tmnxDot1agCfmGlobalOpcodeRx      OBJECT-TYPE
    SYNTAX      Counter32
    MAX-ACCESS  read-only
    STATUS      current
    DESCRIPTION
       "The total number of PDUs received on the node with the specified
        Opcode."
    ::= { tmnxDot1agCfmGlobalOpcodeEntry 2 }

tmnxDot1agCfmGlobalOpcodeTx      OBJECT-TYPE
    SYNTAX      Counter32
    MAX-ACCESS  read-only
    STATUS      current
    DESCRIPTION
       "The total number of PDUs transmitted from the node with the specified
        Opcode."
    ::= { tmnxDot1agCfmGlobalOpcodeEntry 3 }

--
-- Nokia SROS product series dot1ag CFM MEP Creation Table
--
tmnxDot1agCfmMepMgmtTable        OBJECT-TYPE
    SYNTAX      SEQUENCE OF TmnxDot1agCfmMepMgmtEntry
    MAX-ACCESS  not-accessible
    STATUS      current
    DESCRIPTION
        "The tmnxDot1agCfmMepMgmtTable manages the row creation and deletion of
        dot1agCfmMepTable rows. This table replaces the standard row creation
        model for Dot1ag CFM MEPs to better facilitate Nokia SROS
        series requirements. The use of writing to the
        IEEE-8021-CFM-MIB::dot1agCfmMepRowStatus object is deprecated and should
        be discouraged in favor of this table."
    ::= { tmnxDot1agCfmManagementObjects 1 }

tmnxDot1agCfmMepMgmtEntry        OBJECT-TYPE
    SYNTAX      TmnxDot1agCfmMepMgmtEntry
    MAX-ACCESS  not-accessible
    STATUS      current
    DESCRIPTION
        "The tmnxDot1agCfmMepMgmtEntry consists of the configuration objects
        used for the purpose of row creation for Nokia SROS Dot1ag
        MEPs. To create a MEP one must specify its type and endpoint
        association."
    AUGMENTS { dot1agCfmMepEntry }
    ::= { tmnxDot1agCfmMepMgmtTable 1 }

TmnxDot1agCfmMepMgmtEntry        ::= SEQUENCE {
    tmnxDot1agCfmMepMgmtRowStatus    RowStatus,
    tmnxDot1agCfmMepMgmtType         INTEGER,

    -- Virtual MEP Creation
    tmnxDot1agCfmMepMgmtServiceId    TmnxServId,

    -- Standard SAP MEP Creation
    tmnxDot1agCfmMepMgmtIfIndex      InterfaceIndexOrZero,
    tmnxDot1agCfmMepMgmtPrimaryVid   Unsigned32,

    -- Spoke-SDP MEP Creation
    tmnxDot1agCfmMepMgmtSdpId        SdpId,
    tmnxDot1agCfmMepMgmtVcId         Unsigned32,

    -- Facility MEP Creation
    tmnxDot1agCfmMepMgmtFcltyIfIndex InterfaceIndexOrZero,
    tmnxDot1agCfmMepMgmtFcltyVlanId  VlanIdOrNone,

    -- Row Creation Objects
    tmnxDot1agCfmMepMgmtDirection    Dot1agCfmMpDirection
}

tmnxDot1agCfmMepMgmtRowStatus    OBJECT-TYPE
    SYNTAX      RowStatus
    MAX-ACCESS  read-create
    STATUS      current
    DESCRIPTION
        "The value of tmnxDot1agCfmMepMgmtRowStatus specifies the row status of
         the dot1ag CFM MEP. This object replaces the use of the
         IEEE-8021-CFM-MIB::dot1agCfmMepRowStatus object."
    ::= { tmnxDot1agCfmMepMgmtEntry 1 }

tmnxDot1agCfmMepMgmtType         OBJECT-TYPE
    SYNTAX      INTEGER {
                    default           (0),
                    facilityPort      (1),
                    facilityInterface (2),
                    sapPrimaryVlan    (3)
                }
    MAX-ACCESS  read-create
    STATUS      current
    DESCRIPTION
        "The value of tmnxDot1agCfmMepMgmtType specifies the endpoint type that
         this MEP facilitates.
             default           (0) -- implements a traditional MEP.
             facilityPort      (1) -- implements a facility port/LAG level MEP.
             facilityInterface (2) -- implements a router interface level MEP.
             sapPrimaryVlan    (3) -- implements a SAP MEP using primary VLAN-ID
                                      from the MA Comp Table. This is only
                                      applicable if the MA primary VLAN ID is
                                      set to a value other than zero (0).

         This object must be specified during row creation."
    DEFVAL { default }
    ::= { tmnxDot1agCfmMepMgmtEntry 2 }

tmnxDot1agCfmMepMgmtServiceId    OBJECT-TYPE
    SYNTAX      TmnxServId
    MAX-ACCESS  read-create
    STATUS      current
    DESCRIPTION
        "The value of tmnxDot1agCfmMepMgmtServiceId specifies the service to
         which the virtual MEP is attached.

         This object refers directly to
         TIMETRA-IEEE8021-CFM-MIB::tmnxDot1agCfmMepSvcId.

         This object may be specified during row creation when
         tmnxDot1agCfmMepMgmtType is set to the value 'default'."
    ::= { tmnxDot1agCfmMepMgmtEntry 3 }

tmnxDot1agCfmMepMgmtIfIndex      OBJECT-TYPE
    SYNTAX      InterfaceIndexOrZero
    MAX-ACCESS  read-create
    STATUS      current
    DESCRIPTION
        "The value of tmnxDot1agCfmMepMgmtIfIndex specifies, along with
         tmnxDot1agCfmMepMgmtPrimaryVid, the interface index of the interface to
         which the MEP is attached.

         This object refers directly to IEEE8021-CFM-MIB::dot1agCfmMepIfIndex.

         This object may be specified during row creation when
         tmnxDot1agCfmMepMgmtType is set to either the value 'default' or
         'sapPrimaryVlan'."
    ::= { tmnxDot1agCfmMepMgmtEntry 4 }

tmnxDot1agCfmMepMgmtPrimaryVid   OBJECT-TYPE
    SYNTAX      Unsigned32
    MAX-ACCESS  read-create
    STATUS      current
    DESCRIPTION
        "The value of tmnxDot1agCfmMepMgmtPrimaryVid specifies, along with
        tmnxDot1agCfmMepMgmtIfIndex, the Primary VID of the MEP.

         This object refers directly to
         IEEE8021-CFM-MIB::dot1agCfmMepPrimaryVid.

        This object must be specified during row creation when
        tmnxDot1agCfmMepMgmtIfIndex is specified."
    ::= { tmnxDot1agCfmMepMgmtEntry 5 }

tmnxDot1agCfmMepMgmtSdpId        OBJECT-TYPE
    SYNTAX      SdpId
    MAX-ACCESS  read-create
    STATUS      current
    DESCRIPTION
        "The value of tmnxDot1agCfmMepMgmtSdpId specifies, along with
         tmnxDot1agCfmMepMgmtVcId, the SDP-Binding to which the MEP is attached.

         This object refers directly to
         TIMETRA-IEEE8021-CFM-MIB::tmnxDot1agCfmMepSdpId.

         This object may be specified during row creation when
         tmnxDot1agCfmMepMgmtType is set to the value 'default'."
    ::= { tmnxDot1agCfmMepMgmtEntry 6 }

tmnxDot1agCfmMepMgmtVcId         OBJECT-TYPE
    SYNTAX      Unsigned32
    MAX-ACCESS  read-create
    STATUS      current
    DESCRIPTION
        "The value of tmnxDot1agCfmMepMgmtVcId specifies, along with
         tmnxDot1agCfmMepMgmtSdpId, the SDP-Binding to which the MEP is
         attached.

         This object refers directly to
         TIMETRA-IEEE8021-CFM-MIB::tmnxDot1agCfmMepVcId.

         This object must be specified during row creation when
         tmnxDot1agCfmMepMgmtSdpId is specified."
    ::= { tmnxDot1agCfmMepMgmtEntry 7 }

tmnxDot1agCfmMepMgmtFcltyIfIndex OBJECT-TYPE
    SYNTAX      InterfaceIndexOrZero
    MAX-ACCESS  read-create
    STATUS      current
    DESCRIPTION
        "The value of tmnxDot1agCfmMepMgmtFcltyIfIndex specifies, along with
         tmnxDot1agCfmMepMgmtFcltyVlanId, the port or interface to which this
         MEP is attached.

         This object refers directly to
         TIMETRA-IEEE8021-CFM-MIB::tmnxDot1agCfmMepFacilityIfIndex.

         This object must be specified during row creation when
         tmnxDot1agCfmMepMgmtType is set to a 'facility' value."
    ::= { tmnxDot1agCfmMepMgmtEntry 8 }

tmnxDot1agCfmMepMgmtFcltyVlanId  OBJECT-TYPE
    SYNTAX      VlanIdOrNone
    MAX-ACCESS  read-create
    STATUS      current
    DESCRIPTION
        "The value of tmnxDot1agCfmMepMgmtFcltyVlanId specifies, along with
         tmnxDot1agCfmMepMgmtFcltyIfIndex, the port or interface to which this
         MEP is attached.

         This object refers directly to
         TIMETRA-IEEE8021-CFM-MIB::tmnxDot1agCfmMepFacilityVlanId.

         This object must be specified during row creation when
         tmnxDot1agCfmMepMgmtFcltyIfIndex is specified."
    ::= { tmnxDot1agCfmMepMgmtEntry 9 }

tmnxDot1agCfmMepMgmtDirection    OBJECT-TYPE
    SYNTAX      Dot1agCfmMpDirection
    MAX-ACCESS  read-create
    STATUS      current
    DESCRIPTION
        "The value of tmnxDot1agCfmMepMgmtDirection specifies the direction in
         which the MEP faces on the Bridge port.

         This object refers directly to
         IEEE8021-CFM-MIB::dot1agCfmMepDirection.

         This object applies to any MEP type as specified by the object
         tmnxDot1agCfmMepMgmtType."
    DEFVAL { down }
    ::= { tmnxDot1agCfmMepMgmtEntry 50 }

--
-- MEP Eth-Test Result Table
--

tmnxDot1agCfmMepEthTestRsltTable OBJECT-TYPE
    SYNTAX     SEQUENCE OF TmnxDot1agCfmMepEthTestRsltEntry
    MAX-ACCESS not-accessible
    STATUS     current
    DESCRIPTION
       "The tmnxDot1agCfmMepEthTestRsltTable indicates the results of
        all eth-tests indexed by the originating MAC addresses.

        This table is not persistent over reboots of the chassis."
    ::= { tmnxDot1agCfmMep 2 }

tmnxDot1agCfmMepEthTestRsltEntry OBJECT-TYPE
    SYNTAX     TmnxDot1agCfmMepEthTestRsltEntry
    MAX-ACCESS not-accessible
    STATUS     current
    DESCRIPTION
       "The MEG result table."
    INDEX {
              dot1agCfmMdIndex,
              dot1agCfmMaIndex,
              dot1agCfmMepIdentifier,
              tmnxDot1agCfmMepSrcMacAddress
          }
    ::= { tmnxDot1agCfmMepEthTestRsltTable 1 }

TmnxDot1agCfmMepEthTestRsltEntry ::= SEQUENCE {
    tmnxDot1agCfmMepSrcMacAddress    MacAddress,
    tmnxDot1agCfmMepFrameCount       Counter32,
    tmnxDot1agCfmMepByteCount        Counter32,
    tmnxDot1agCfmMepFailedBits       Counter32,
    tmnxDot1agCfmMepCrcFailures      Counter32,
    tmnxDot1agCfmMepCurrByteCount    Gauge32,
    tmnxDot1agCfmMepCurrFailedBits   Gauge32,
    tmnxDot1agCfmMepCurrCrcFailures  TruthValue
}

tmnxDot1agCfmMepSrcMacAddress    OBJECT-TYPE
    SYNTAX     MacAddress
    MAX-ACCESS not-accessible
    STATUS     current
    DESCRIPTION
        "The value of tmnxDot1agCfmMepSrcMacAddress indicates the MAC address
         of the issuer of the eth-test."
    ::= { tmnxDot1agCfmMepEthTestRsltEntry 1 }

tmnxDot1agCfmMepFrameCount       OBJECT-TYPE
    SYNTAX     Counter32
    MAX-ACCESS read-only
    STATUS     current
    DESCRIPTION
        "The value of tmnxDot1agCfmMepFrameCount indicates the number of frames
         received from the issuer of the eth-test."
    ::= { tmnxDot1agCfmMepEthTestRsltEntry 2 }

tmnxDot1agCfmMepByteCount        OBJECT-TYPE
    SYNTAX     Counter32
    MAX-ACCESS read-only
    STATUS     current
    DESCRIPTION
        "The value of tmnxDot1agCfmMepByteCount indicates the number of bytes
         received from the issuer of the eth-test."
    ::= { tmnxDot1agCfmMepEthTestRsltEntry 3 }

tmnxDot1agCfmMepFailedBits       OBJECT-TYPE
    SYNTAX     Counter32
    MAX-ACCESS read-only
    STATUS     current
    DESCRIPTION
        "The value of tmnxDot1agCfmMepFailedBits indicates the accumulated
         number of bits that did not match the test-pattern in all received
         Eth-Tst frames since tmnxDot1agCfmMepEthTestEnable is configured
         from 'false' to 'true'."
    ::= { tmnxDot1agCfmMepEthTestRsltEntry 4 }

tmnxDot1agCfmMepCrcFailures      OBJECT-TYPE
    SYNTAX     Counter32
    MAX-ACCESS read-only
    STATUS     current
    DESCRIPTION
        "The value of tmnxDot1agCfmMepCrcFailures indicates the accumulated
         number of CRC checksum failures."
    ::= { tmnxDot1agCfmMepEthTestRsltEntry 5 }

tmnxDot1agCfmMepCurrByteCount    OBJECT-TYPE
    SYNTAX     Gauge32
    MAX-ACCESS read-only
    STATUS     current
    DESCRIPTION
        "The value of tmnxDot1agCfmMepCurrByteCount indicates the number of
         bytes contained in the most recently received Eth-Tst frame Test TLV."
    ::= { tmnxDot1agCfmMepEthTestRsltEntry 6 }

tmnxDot1agCfmMepCurrFailedBits   OBJECT-TYPE
    SYNTAX     Gauge32
    MAX-ACCESS read-only
    STATUS     current
    DESCRIPTION
        "The value of tmnxDot1agCfmMepCurrFailedBits indicates the number of
         bits that did not match the test-pattern in the most recently received
         Eth-Tst frame."
    ::= { tmnxDot1agCfmMepEthTestRsltEntry 7 }

tmnxDot1agCfmMepCurrCrcFailures  OBJECT-TYPE
    SYNTAX     TruthValue
    MAX-ACCESS read-only
    STATUS     current
    DESCRIPTION
        "The value of tmnxDot1agCfmMepCurrCrcFailures indicates that CRC errors
         were detected in the most recently received Eth-Tst frame."
    ::= { tmnxDot1agCfmMepEthTestRsltEntry 8 }

--
-- MEP Delay Result Table
--
tmnxDot1agCfmMepDelayRsltTable   OBJECT-TYPE
    SYNTAX     SEQUENCE OF TmnxDot1agCfmMepDelayRsltEntry
    MAX-ACCESS not-accessible
    STATUS     current
    DESCRIPTION
       "The tmnxDot1agCfmMepDelayRsltTable indicates the results of
        all the One-Way/Two-Way Delay Tests from the originating MAC
        addresses.

        This table is not persistent over reboots of the chassis."
    ::= { tmnxDot1agCfmMep 3 }

tmnxDot1agCfmMepDelayRsltEntry   OBJECT-TYPE
    SYNTAX     TmnxDot1agCfmMepDelayRsltEntry
    MAX-ACCESS not-accessible
    STATUS     current
    DESCRIPTION
       "The MEG result table."
    INDEX {
              dot1agCfmMdIndex,
              dot1agCfmMaIndex,
              dot1agCfmMepIdentifier,
              tmnxDot1agCfmMepDelaySrcMacAddr,
              tmnxDot1agCfmMepDelayTestType
          }
    ::= { tmnxDot1agCfmMepDelayRsltTable 1 }

TmnxDot1agCfmMepDelayRsltEntry   ::= SEQUENCE {
    tmnxDot1agCfmMepDelaySrcMacAddr  MacAddress,
    tmnxDot1agCfmMepDelayTestType    INTEGER,
    tmnxDot1agCfmMepDelayTestDelay   Integer32,
    tmnxDot1agCfmMepDelayVariation   Unsigned32
}

tmnxDot1agCfmMepDelaySrcMacAddr  OBJECT-TYPE
    SYNTAX     MacAddress
    MAX-ACCESS not-accessible
    STATUS     current
    DESCRIPTION
        "The value of tmnxDot1agCfmMepDelaySrcMacAddr indicates the source
         MAC address of the issuer of the test."
    ::= { tmnxDot1agCfmMepDelayRsltEntry 1 }

tmnxDot1agCfmMepDelayTestType    OBJECT-TYPE
    SYNTAX     INTEGER {
                   oneWayTest (1),
                   twoWayTest (2)
               }
    MAX-ACCESS not-accessible
    STATUS     current
    DESCRIPTION
        "The value of tmnxDot1agCfmMepDelayTestType indicates the type
         of test this row details."
    ::= { tmnxDot1agCfmMepDelayRsltEntry 2 }

tmnxDot1agCfmMepDelayTestDelay   OBJECT-TYPE
    SYNTAX     Integer32
    UNITS      "microseconds"
    MAX-ACCESS read-only
    STATUS     current
    DESCRIPTION
        "The value of tmnxDot1agCfmMepDelayTestDelay indicates the amount
         of time, measured in microseconds, from when the test-frame was
         transmitted to the time it was received minus the local processing time
         taken by the remote system."
    ::= { tmnxDot1agCfmMepDelayRsltEntry 3 }

tmnxDot1agCfmMepDelayVariation   OBJECT-TYPE
    SYNTAX     Unsigned32
    UNITS      "microseconds"
    MAX-ACCESS read-only
    STATUS     current
    DESCRIPTION
        "The value of tmnxDot1agCfmMepDelayVariation indicates the amount
         of time delay variation, measured in microseconds, from the two
         most recent time delay measurements"
    ::= { tmnxDot1agCfmMepDelayRsltEntry 4 }

--
-- MEP Synthetic Loss Measurement two-way Test Config Table
--
tmnxDot1agCfmMepSlmTWTestTable   OBJECT-TYPE
    SYNTAX      SEQUENCE OF TmnxDot1agCfmMepSlmTWTestEntry
    MAX-ACCESS  not-accessible
    STATUS      current
    DESCRIPTION
        "tmnxDot1agCfmMepSlmTWTestTable consists of the MEP configuration for
         issuing individual Synthetic Loss Measurement tests."
    REFERENCE "ITU-T Y.1731 Ethernet Synthetic Frame Loss Measurement (ETH-SLM)"
    ::= { tmnxDot1agCfmMep 4 }

tmnxDot1agCfmMepSlmTWTestEntry   OBJECT-TYPE
    SYNTAX      TmnxDot1agCfmMepSlmTWTestEntry
    MAX-ACCESS  not-accessible
    STATUS      current
    DESCRIPTION
        "tmnxDot1agCfmMepSlmTWTestEntry contains the configuration for
         generating Synthetic Loss Measurement (SLM) Tests for a particular MEP.
         A row exists for each row in the dot1agCfmMepTable, and is destroyed
         automatically with the removal of a row in the dot1agCfmMepTable.

         Results from a two-way SLM test are reported in
         tmnxDot1agCfmMepSlmTestRsltTable with the tmnxDot1agCfmMepSlmTestType
         set to 'twoWayTest (2)'."
    AUGMENTS { dot1agCfmMepEntry }
    ::= { tmnxDot1agCfmMepSlmTWTestTable 1 }

TmnxDot1agCfmMepSlmTWTestEntry   ::= SEQUENCE {
    tmnxDot1agCfmMepSlmTWTestStatus  TmnxEnabledDisabled,
    tmnxDot1agCfmMepSlmTWTestId      Unsigned32,
    tmnxDot1agCfmMepSlmTWMacAddress  MacAddress,
    tmnxDot1agCfmMepSlmTWPriority    Unsigned32,
    tmnxDot1agCfmMepSlmTWInterval    Unsigned32,
    tmnxDot1agCfmMepSlmTWTimeout     Unsigned32,
    tmnxDot1agCfmMepSlmTWDataSize    Unsigned32,
    tmnxDot1agCfmMepSlmTWSendCount   Unsigned32,
    tmnxDot1agCfmMepSlmTWIntrvlUnits INTEGER
}

tmnxDot1agCfmMepSlmTWTestStatus  OBJECT-TYPE
    SYNTAX      TmnxEnabledDisabled
    MAX-ACCESS  read-create
    STATUS      current
    DESCRIPTION
        "The value of tmnxDot1agCfmMepSlmTWTestStatus specifies the operational
         state of the two-way Synthetic Loss Measurement (SLM) test.

         To issue a two-way SLM test the user must issue an SNMP SET on this
         object with a value 'enabled (1)'. To abort the two-way SLM test issue
         an SNMP SET on this object with the value 'disabled (2)'.

         A read on this object represents the current state of the two-way SLM
         test:
             enabled  (1)  - The test is actively running, and attempts at
                             modifying any two-way SLM object will be rejected
             disabled (2)  - The test is not running.

         Once the test is complete this object will revert to the default value
         'disabled (2)'."
    DEFVAL { disabled }
    ::= { tmnxDot1agCfmMepSlmTWTestEntry 1 }

tmnxDot1agCfmMepSlmTWTestId      OBJECT-TYPE
    SYNTAX      Unsigned32
    MAX-ACCESS  read-only
    STATUS      current
    DESCRIPTION
        "The value of tmnxDot1agCfmMepSlmTWTestId indicates the test identifier
         used to initiate the two-way Synthetic Loss Measurement (SLM) test."
    ::= { tmnxDot1agCfmMepSlmTWTestEntry 2 }

tmnxDot1agCfmMepSlmTWMacAddress  OBJECT-TYPE
    SYNTAX      MacAddress
    MAX-ACCESS  read-create
    STATUS      current
    DESCRIPTION
        "The value of tmnxDot1agCfmMepSlmTWMacAddress specifies the MAC address
         used as a target for the two-way Synthetic Loss Measurement (SLM) test.

         This object MUST be set to a valid MAC Address for proper execution of
         the two-way SLM test."
    DEFVAL { '000000000000'H }
    ::= { tmnxDot1agCfmMepSlmTWTestEntry 3 }

tmnxDot1agCfmMepSlmTWPriority    OBJECT-TYPE
    SYNTAX     Unsigned32 (0..7)
    MAX-ACCESS read-create
    STATUS     current
    DESCRIPTION
        "The value of tmnxDot1agCfmMepSlmTWPriority specifies the priority used
         in the generated test frame for the two-way Synthetic Loss Measurement
         (SLM) test."
    DEFVAL { 7 }
    ::= { tmnxDot1agCfmMepSlmTWTestEntry 4 }

tmnxDot1agCfmMepSlmTWInterval    OBJECT-TYPE
    SYNTAX      Unsigned32 (1..90)
    MAX-ACCESS  read-create
    STATUS      current
    DESCRIPTION
        "The value of tmnxDot1agCfmMepSlmTWInterval, in conjunction with
         tmnxDot1agCfmMepSlmTWIntrvlUnits, specifies the interval between
         Synthetic Loss Measurement (SLM) messages sent by the two-way SLM test.
         For example, if tmnxDot1agCfmMepSlmTWInterval has the value 90, and
         tmnxDot1agCfmMepSlmTWIntrvlUnits has the value 'centiseconds(2)', the
         interval between SLM messages is 0.9 seconds.

         The tmnxDot1agCfmMepSlmTWInterval and tmnxDot1agCfmMepSlmTWIntrvlUnits
         pair provide support for the following intervals:
           0.1, 0.2, 0.3, 0.4, 0.5, 0.6, 0.7, 0.8, 0.9 seconds;
           1, 2, 3, 4, 5, 6, 7, 8, 9, 10 seconds."
    DEFVAL { 5 }
    ::= { tmnxDot1agCfmMepSlmTWTestEntry 5 }

tmnxDot1agCfmMepSlmTWTimeout     OBJECT-TYPE
    SYNTAX      Unsigned32 (1..10)
    UNITS       "seconds"
    MAX-ACCESS  read-create
    STATUS      current
    DESCRIPTION
        "The value of tmnxDot1agCfmMepSlmTWTimeout specifies the time-out value,
         in seconds, to wait for a Synthetic Loss Measurement (SLM) message to
         reply for the two-way SLM test. Upon expiration of the timeout period,
         the agent assumes that the message response will not be received. Any
         response received after the timeout period has expired is silently
         discarded."
    DEFVAL { 5 }
    ::= { tmnxDot1agCfmMepSlmTWTestEntry 6 }

tmnxDot1agCfmMepSlmTWDataSize    OBJECT-TYPE
    SYNTAX      Unsigned32 (0..1500)
    UNITS       "bytes"
    MAX-ACCESS  read-create
    STATUS      current
    DESCRIPTION
        "The value of tmnxDot1agCfmMepSlmTWDataSize specifies the data size,
         in bytes, contained in the padding TLV for the two-way Synthetic Loss
         Measurement (SLM) test. A value of zero (0) specifies that no padding
         TLV is inserted in the SLM packet. Any non-zero value will increase
         the packet size by the specified data size plus 3 bytes for the TLV
         header."
    DEFVAL { 0 }
    ::= { tmnxDot1agCfmMepSlmTWTestEntry 7 }

tmnxDot1agCfmMepSlmTWSendCount   OBJECT-TYPE
    SYNTAX      Unsigned32(1..1000)
    UNITS       "packets"
    MAX-ACCESS  read-create
    STATUS      current
    DESCRIPTION
        "The value of tmnxDot1agCfmMepSlmTWSendCount specifies the number of
         Synthetic Loss Measurement (SLM) packets to send during the two-way
         SLM test."
    DEFVAL { 1 }
    ::= { tmnxDot1agCfmMepSlmTWTestEntry 8 }

tmnxDot1agCfmMepSlmTWIntrvlUnits OBJECT-TYPE
    SYNTAX      INTEGER {
                    seconds(1),
                    centiseconds(2)
                }
    MAX-ACCESS  read-create
    STATUS      current
    DESCRIPTION
        "The value of tmnxDot1agCfmMepSlmTWIntrvlUnits, in conjunction with
         tmnxDot1agCfmMepSlmTWInterval, specifies the interval between Synthetic
         Loss Measurement (SLM) messages sent by the two-way SLM test.  For
         example, if tmnxDot1agCfmMepSlmTWInterval has the value 90, and
         tmnxDot1agCfmMepSlmTWIntrvlUnits has the value 'centiseconds(2)', the
         interval between SLM messages is 0.9 seconds.

         The intervals supported are shown in the tmnxDot1agCfmMepSlmTWInterval
         DESCRIPTION clause."
    DEFVAL { seconds }
    ::= { tmnxDot1agCfmMepSlmTWTestEntry 9 }

--
-- MEP Synthetic Loss Measurement one-way Test Config Table
--
tmnxDot1agCfmMepSlmOWTestTable   OBJECT-TYPE
    SYNTAX      SEQUENCE OF TmnxDot1agCfmMepSlmOWTestEntry
    MAX-ACCESS  not-accessible
    STATUS      current
    DESCRIPTION
        "tmnxDot1agCfmMepSlmOWTestTable consists of the MEP configuration for
         issuing individual Synthetic Loss Measurement one-way tests."
    REFERENCE "ITU-T Y.1731 Ethernet Synthetic Frame Loss Measurement (ETH-SLM)"
    ::= { tmnxDot1agCfmMep 5 }

tmnxDot1agCfmMepSlmOWTestEntry   OBJECT-TYPE
    SYNTAX      TmnxDot1agCfmMepSlmOWTestEntry
    MAX-ACCESS  not-accessible
    STATUS      current
    DESCRIPTION
        "tmnxDot1agCfmMepSlmOWTestEntry contains the configuration for
         generating Synthetic Loss Measurement (SLM) Tests for a particular MEP.
         A row exists for each row in the dot1agCfmMepTable, and is destroyed
         automatically with the removal of a row in the dot1agCfmMepTable.

         Results from a one-way SLM test are reported in
         tmnxDot1agCfmMepSlmTestRsltTable with tmnxDot1agCfmMepSlmTestType set
         to 'oneWayTest (1)'."
    AUGMENTS { dot1agCfmMepEntry }
    ::= { tmnxDot1agCfmMepSlmOWTestTable 1 }

TmnxDot1agCfmMepSlmOWTestEntry   ::= SEQUENCE {
    tmnxDot1agCfmMepSlmOWTestStatus  TmnxEnabledDisabled,
    tmnxDot1agCfmMepSlmOWTestId      Unsigned32,
    tmnxDot1agCfmMepSlmOWMacAddress  MacAddress,
    tmnxDot1agCfmMepSlmOWPriority    Unsigned32,
    tmnxDot1agCfmMepSlmOWInterval    Unsigned32,
    tmnxDot1agCfmMepSlmOWDataSize    Unsigned32,
    tmnxDot1agCfmMepSlmOWSendCount   Unsigned32
}

tmnxDot1agCfmMepSlmOWTestStatus  OBJECT-TYPE
    SYNTAX      TmnxEnabledDisabled
    MAX-ACCESS  read-create
    STATUS      current
    DESCRIPTION
        "The value of tmnxDot1agCfmMepSlmOWTestStatus specifies the operational
         state of the one-way Synthetic Loss Measurement (SLM) test.

         To issue a one-way SLM test the user must issue an SNMP SET on this
         object with a value 'enabled (1)'. To abort the one-way SLM test issue
         an SNMP SET on this object with the value 'disabled (2)'.

         A read on this object represents the current state of the one-way SLM
         test:
             enabled  (1)  - The test is actively running, and attempts at
                             modifying any one-way SLM object will be rejected
             disabled (2)  - The test is not running.

         Once the test is complete this object will revert to the default value
         'disabled (2)'."
    DEFVAL { disabled }
    ::= { tmnxDot1agCfmMepSlmOWTestEntry 1 }

tmnxDot1agCfmMepSlmOWTestId      OBJECT-TYPE
    SYNTAX      Unsigned32
    MAX-ACCESS  read-only
    STATUS      current
    DESCRIPTION
        "The value of tmnxDot1agCfmMepSlmOWTestId indicates the test identifier
         used to initiate the one-way Synthetic Loss Measurement (SLM) test."
    ::= { tmnxDot1agCfmMepSlmOWTestEntry 2 }

tmnxDot1agCfmMepSlmOWMacAddress  OBJECT-TYPE
    SYNTAX      MacAddress
    MAX-ACCESS  read-create
    STATUS      current
    DESCRIPTION
        "The value of tmnxDot1agCfmMepSlmOWMacAddress specifies the MAC address
         used as a target for the one-way Synthetic Loss Measurement (SLM) Test.

         This object MUST be set to a valid MAC Address for proper execution of
         the one-way SLM test."
    DEFVAL { '000000000000'H }
    ::= { tmnxDot1agCfmMepSlmOWTestEntry 3 }

tmnxDot1agCfmMepSlmOWPriority    OBJECT-TYPE
    SYNTAX     Unsigned32 (0..7)
    MAX-ACCESS read-create
    STATUS     current
    DESCRIPTION
        "The value of tmnxDot1agCfmMepSlmOWPriority specifies the priority used
         in the generated test frame for the one-way Synthetic Loss Measurement
         (SLM) test."
    DEFVAL { 7 }
    ::= { tmnxDot1agCfmMepSlmOWTestEntry 4 }

tmnxDot1agCfmMepSlmOWInterval    OBJECT-TYPE
    SYNTAX      Unsigned32 (1..10)
    UNITS       "seconds"
    MAX-ACCESS  read-create
    STATUS      current
    DESCRIPTION
        "The value of tmnxDot1agCfmMepSlmOWInterval specifies the delay, in
        seconds, between Synthetic Loss Measurement (SLM) messages for the
        one-way SLM test."
    DEFVAL { 5 }
    ::= { tmnxDot1agCfmMepSlmOWTestEntry 5 }

tmnxDot1agCfmMepSlmOWDataSize    OBJECT-TYPE
    SYNTAX      Unsigned32 (0..1500)
    UNITS       "bytes"
    MAX-ACCESS  read-create
    STATUS      current
    DESCRIPTION
        "The value of tmnxDot1agCfmMepSlmOWDataSize specifies the data size,
         in bytes, contained in the padding TLV for the one-way Synthetic Loss
         Measurement (SLM) test. A value of zero (0) specifies that no padding
         TLV is inserted in the SLM packet. Any non-zero value will increase
         the packet size by the specified data size plus 3 bytes for the TLV
         header."
    DEFVAL { 0 }
    ::= { tmnxDot1agCfmMepSlmOWTestEntry 6 }

tmnxDot1agCfmMepSlmOWSendCount   OBJECT-TYPE
    SYNTAX      Unsigned32(1..100)
    UNITS       "packets"
    MAX-ACCESS  read-create
    STATUS      current
    DESCRIPTION
        "The value of tmnxDot1agCfmMepSlmOWSendCount specifies the number of
         Synthetic Loss Measurement (SLM) packets to send consecutively during
         the one-way SLM test."
    DEFVAL { 1 }
    ::= { tmnxDot1agCfmMepSlmOWTestEntry 7 }

--
-- MEP Synthetic Loss Measurement Test Results Table
--
tmnxDot1agCfmMepSlmTestRsltTable OBJECT-TYPE
    SYNTAX      SEQUENCE OF TmnxDot1agCfmMepSlmTestRsltEntry
    MAX-ACCESS  not-accessible
    STATUS      current
    DESCRIPTION
        "tmnxDot1agCfmMepSlmTestRsltTable consists of the results of manually
         triggered Synthetic Loss Measurement tests."
    ::= { tmnxDot1agCfmMep 6 }

tmnxDot1agCfmMepSlmTestRsltEntry OBJECT-TYPE
    SYNTAX      TmnxDot1agCfmMepSlmTestRsltEntry
    MAX-ACCESS  not-accessible
    STATUS      current
    DESCRIPTION
        "tmnxDot1agCfmMepSlmTestRsltEntry contains the results of a
         manually triggered Synthetic Loss Measurement (SLM) test for a
         particular MEP. Rows are auto-generated by the system based on the
         issuing of a SLM test."
    INDEX {
              dot1agCfmMdIndex,
              dot1agCfmMaIndex,
              dot1agCfmMepIdentifier,
              tmnxDot1agCfmMepSlmTestType,
              tmnxDot1agCfmMepSlmRemoteMacAddr
          }
    ::= { tmnxDot1agCfmMepSlmTestRsltTable 1 }

TmnxDot1agCfmMepSlmTestRsltEntry ::= SEQUENCE {
    tmnxDot1agCfmMepSlmTestType      INTEGER,
    tmnxDot1agCfmMepSlmRemoteMacAddr MacAddress,
    tmnxDot1agCfmMepSlmTestId        Unsigned32,
    tmnxDot1agCfmMepSlmRemoteMepId   Dot1agCfmMepIdOrZero,
    tmnxDot1agCfmMepSlmLastTxSeqF    Unsigned32,
    tmnxDot1agCfmMepSlmPacketIn      Counter32,
    tmnxDot1agCfmMepSlmPacketLossIn  Integer32,
    tmnxDot1agCfmMepSlmPacketLossOut Integer32,
    tmnxDot1agCfmMepSlmPacketUnack   Gauge32
}

tmnxDot1agCfmMepSlmTestType      OBJECT-TYPE
    SYNTAX      INTEGER {
                  oneWayTest (1),
                  twoWayTest (2)
                }
    MAX-ACCESS  not-accessible
    STATUS      current
    DESCRIPTION
        "The value of tmnxDot1agCfmMepSlmTestType specifies whether the
         row for this Synthetic Loss Measurement (SLM) test refers to a two-way
         SLM test."
    ::= { tmnxDot1agCfmMepSlmTestRsltEntry 1 }

tmnxDot1agCfmMepSlmRemoteMacAddr OBJECT-TYPE
    SYNTAX      MacAddress
    MAX-ACCESS  not-accessible
    STATUS      current
    DESCRIPTION
        "The value of tmnxDot1agCfmMepSlmRemoteMacAddr specifies the source MAC
         address of the remote node involved in the test."
    ::= { tmnxDot1agCfmMepSlmTestRsltEntry 2 }

tmnxDot1agCfmMepSlmTestId        OBJECT-TYPE
    SYNTAX      Unsigned32
    MAX-ACCESS  read-only
    STATUS      current
    DESCRIPTION
        "The value of tmnxDot1agCfmMepSlmTestId indicates the test identifier
         that was used to initiate the Synthetic Loss Measurement (SLM) test."
    ::= { tmnxDot1agCfmMepSlmTestRsltEntry 3 }

tmnxDot1agCfmMepSlmRemoteMepId   OBJECT-TYPE
    SYNTAX      Dot1agCfmMepIdOrZero
    MAX-ACCESS  read-only
    STATUS      current
    DESCRIPTION
        "The value of tmnxDot1agCfmMepSlmRemoteMepId indicates the MEP
         Identifier of the remote node involved in the test.

         Zero indicates that the remote node did not provide a MEP Identifier.
         For example, zero is returned if the local node timed out while waiting
         for a probe response for each probe sent for the test."
    ::= { tmnxDot1agCfmMepSlmTestRsltEntry 4 }

tmnxDot1agCfmMepSlmLastTxSeqF    OBJECT-TYPE
    SYNTAX      Unsigned32
    MAX-ACCESS  read-only
    STATUS      current
    DESCRIPTION
        "The value of tmnxDot1agCfmMepSlmLastTxSeqF indicates the last
         received sequence number on the local node, transmitted by the
         remote node."
    REFERENCE "ITU-T Y.1731 Ethernet Synthetic Frame Loss Measurement (ETH-SLM)"
    ::= { tmnxDot1agCfmMepSlmTestRsltEntry 5 }

tmnxDot1agCfmMepSlmPacketIn      OBJECT-TYPE
    SYNTAX      Counter32
    UNITS       "packets"
    MAX-ACCESS  read-only
    STATUS      current
    DESCRIPTION
        "The value of tmnxDot1agCfmMepSlmPacketIn indicates the number of
         packets received during the execution of the test."
    REFERENCE "ITU-T Y.1731 Ethernet Synthetic Frame Loss Measurement (ETH-SLM)"
    ::= { tmnxDot1agCfmMepSlmTestRsltEntry 6 }

tmnxDot1agCfmMepSlmPacketLossIn  OBJECT-TYPE
    SYNTAX      Integer32
    UNITS       "packets"
    MAX-ACCESS  read-only
    STATUS      current
    DESCRIPTION
        "The value of tmnxDot1agCfmMepSlmPacketLossIn indicates the number of
         packets transmitted from the remote node but not received on the local
         node during the execution of the test."
    REFERENCE "ITU-T Y.1731 Ethernet Synthetic Frame Loss Measurement (ETH-SLM)"
    ::= { tmnxDot1agCfmMepSlmTestRsltEntry 7 }

tmnxDot1agCfmMepSlmPacketLossOut OBJECT-TYPE
    SYNTAX      Integer32
    UNITS       "packets"
    MAX-ACCESS  read-only
    STATUS      current
    DESCRIPTION
        "The value of tmnxDot1agCfmMepSlmPacketLossOut indicates the number of
         packets transmitted from the local node but not received on the remote
         node during the execution of the test."
    REFERENCE "ITU-T Y.1731 Ethernet Synthetic Frame Loss Measurement (ETH-SLM)"
    ::= { tmnxDot1agCfmMepSlmTestRsltEntry 8 }

tmnxDot1agCfmMepSlmPacketUnack   OBJECT-TYPE
    SYNTAX      Gauge32
    UNITS       "packets"
    MAX-ACCESS  read-only
    STATUS      current
    DESCRIPTION
        "The value of tmnxDot1agCfmMepSlmPacketUnack indicates the number of
         unacknowledged lost packets during the execution of the test."
    REFERENCE "ITU-T Y.1731 Ethernet Synthetic Frame Loss Measurement (ETH-SLM)"
    ::= { tmnxDot1agCfmMepSlmTestRsltEntry 9 }

--
-- MEP Multicast Loopback Results Table
--
tmnxDot1agCfmMepMcstLbmRsltTable OBJECT-TYPE
    SYNTAX      SEQUENCE OF TmnxDot1agCfmMepMcstLbmRsltEntry
    MAX-ACCESS  not-accessible
    STATUS      current
    DESCRIPTION
        "tmnxDot1agCfmMepMcstLbmRsltTable consists of the results of manually
         triggered ETH-CFM loopback tests where the value of
         dot1agCfmMepTransmitLbmDestMacAddress was set to the multicast
         MAC address for the MEP.

         Only one result set per MEP is retained."
    ::= { tmnxDot1agCfmMep 7 }

tmnxDot1agCfmMepMcstLbmRsltEntry OBJECT-TYPE
    SYNTAX      TmnxDot1agCfmMepMcstLbmRsltEntry
    MAX-ACCESS  not-accessible
    STATUS      current
    DESCRIPTION
        "tmnxDot1agCfmMepMcstLbmRsltEntry contains an individual message
         response to a manually triggered loopback test.

         A row is auto-generated by the system upon receipt of a valid loopback
         response that matches a multicast loopback test in progress."
    INDEX {
              dot1agCfmMdIndex,
              dot1agCfmMaIndex,
              dot1agCfmMepIdentifier,
              tmnxDot1agCfmMepLbmRemoteMepMac,
              tmnxDot1agCfmMepLbmSeqNumber,
              tmnxDot1agCfmMepLbmRxIndex
          }
    ::= { tmnxDot1agCfmMepMcstLbmRsltTable 1 }

TmnxDot1agCfmMepMcstLbmRsltEntry ::= SEQUENCE {
    tmnxDot1agCfmMepLbmRemoteMepMac  MacAddress,
    tmnxDot1agCfmMepLbmSeqNumber     Unsigned32,
    tmnxDot1agCfmMepLbmRxIndex       Unsigned32
}

tmnxDot1agCfmMepLbmRemoteMepMac  OBJECT-TYPE
    SYNTAX      MacAddress
    MAX-ACCESS  not-accessible
    STATUS      current
    DESCRIPTION
        "The value of tmnxDot1agCfmMepLbmRemoteMepMac specifies the MAC address
         of the remote MEP responding to the multicast loopback message."
    ::= { tmnxDot1agCfmMepMcstLbmRsltEntry 1 }

tmnxDot1agCfmMepLbmSeqNumber     OBJECT-TYPE
    SYNTAX      Unsigned32
    MAX-ACCESS  not-accessible
    STATUS      current
    DESCRIPTION
        "The value of tmnxDot1agCfmMepLbmSeqNumber specifies the sequence
         number contained within the reply message."
    ::= { tmnxDot1agCfmMepMcstLbmRsltEntry 2 }

tmnxDot1agCfmMepLbmRxIndex       OBJECT-TYPE
    SYNTAX      Unsigned32
    MAX-ACCESS  read-only
    STATUS      current
    DESCRIPTION
        "The value of tmnxDot1agCfmMepLbmRxIndex indicates the order in which
         the reply was received for the corresponding remote MAC address.  It
         is locally assigned and can be used to detect out of order responses."
    ::= { tmnxDot1agCfmMepMcstLbmRsltEntry 3 }

--
-- The MEP Database Table (Augment)
--
-- Use of AUGMENTS clause implies a one-to-one dependent relationship between
-- the base table, dot1agCfmMepDbTable, and the augmenting table,
-- tmnxDot1agCfmMepDbTable, with additional columns. Creation (or deletion) of a
-- row in the dot1agCfmMepDbTable results in the same fate for the row in the
-- tmnxDot1agCfmMepDbTable.
tmnxDot1agCfmMepDbTable          OBJECT-TYPE
    SYNTAX      SEQUENCE OF TmnxDot1agCfmMepDbEntry
    MAX-ACCESS  not-accessible
    STATUS      current
    DESCRIPTION
        "tmnxDot1agCfmMepDbTable is an augmented table for the standard
         IEEE8021-CFM table dot1agCfmMepDbTable."
    ::= { tmnxDot1agCfmMep 8 }

tmnxDot1agCfmMepDbEntry          OBJECT-TYPE
    SYNTAX      TmnxDot1agCfmMepDbEntry
    MAX-ACCESS  not-accessible
    STATUS      current
    DESCRIPTION
        "tmnxDot1agCfmMepDbEntry is an augmented conceptual row in the
        dot1agCfmMepDbTable. Objects defined in this row extend the
        functionality of the base row.

        Creation and deletion of rows in this table is managed through the
        base table."
    AUGMENTS { dot1agCfmMepDbEntry }
    ::= { tmnxDot1agCfmMepDbTable 1 }

TmnxDot1agCfmMepDbEntry          ::= SEQUENCE {
    tmnxDot1agCfmMepDbGraceRx        TruthValue
}

tmnxDot1agCfmMepDbGraceRx        OBJECT-TYPE
    SYNTAX      TruthValue
    MAX-ACCESS  read-only
    STATUS      current
    DESCRIPTION
       "The value of tmnxDot1agCfmMepDbGraceRx indicates whether the
        remote peer is transmitting a grace period notification or not."
    ::= { tmnxDot1agCfmMepDbEntry 1 }

--
-- MEP Per OpCode Statistics Table
--
tmnxDot1agCfmMepOpcodeTable      OBJECT-TYPE
    SYNTAX      SEQUENCE OF TmnxDot1agCfmMepOpcodeEntry
    MAX-ACCESS  not-accessible
    STATUS      current
    DESCRIPTION
       "tmnxDot1agCfmMepOpcodeTable consists of statistics that are kept
        in the receive and transmit direction on a MEP for each CFM PDU
        Opcode."
    REFERENCE
       "Y.1731 clauses 8 and 9"
    ::= { tmnxDot1agCfmMep 9 }

tmnxDot1agCfmMepOpcodeEntry      OBJECT-TYPE
    SYNTAX      TmnxDot1agCfmMepOpcodeEntry
    MAX-ACCESS  not-accessible
    STATUS      current
    DESCRIPTION
       "A Mep Opcode Stats Table entry."
    INDEX {
              dot1agCfmMdIndex,
              dot1agCfmMaIndex,
              dot1agCfmMepIdentifier,
              tmnxDot1agCfmMepOpcode
          }
    ::= { tmnxDot1agCfmMepOpcodeTable 1 }

TmnxDot1agCfmMepOpcodeEntry      ::= SEQUENCE {
      tmnxDot1agCfmMepOpcode            Dot1agCfmStatisticOpcodeName,
      tmnxDot1agCfmMepOpcodeRx          Counter32,
      tmnxDot1agCfmMepOpcodeTx          Counter32
    }

tmnxDot1agCfmMepOpcode           OBJECT-TYPE
    SYNTAX Dot1agCfmStatisticOpcodeName
    MAX-ACCESS  not-accessible
    STATUS      current
    DESCRIPTION
       "The value of tmnxDot1agCfmMepOpcode specifies the CFM PDU Opcode to
        which the statistics refer."
    ::= { tmnxDot1agCfmMepOpcodeEntry 1 }

tmnxDot1agCfmMepOpcodeRx         OBJECT-TYPE
    SYNTAX      Counter32
    MAX-ACCESS  read-only
    STATUS      current
    DESCRIPTION
       "The total number of PDUs received on the MEP with the specified Opcode."
    ::= { tmnxDot1agCfmMepOpcodeEntry 2 }

tmnxDot1agCfmMepOpcodeTx         OBJECT-TYPE
    SYNTAX      Counter32
    MAX-ACCESS  read-only
    STATUS      current
    DESCRIPTION
       "The total number of PDUs transmitted from the MEP with the specified
        Opcode."
    ::= { tmnxDot1agCfmMepOpcodeEntry 3 }

-- Nokia SROS product series CFM MIP table
--
-- The MIP tables (Sap and SDP) represent all the service endpoints
-- where Maintenance Domain Intermediate Point (MIP) creation can
-- occur.  If a SAP or SDP-Binding does not have a correlating row
-- in these tables, then no MIP will be created for that endpoint.
--
-- ******************************************************************
-- The MIP (SAP) Table
-- ******************************************************************
--
tmnxDot1agCfmSapMipTable         OBJECT-TYPE
    SYNTAX     SEQUENCE OF TmnxDot1agCfmSapMipEntry
    MAX-ACCESS not-accessible
    STATUS     current
    DESCRIPTION
       "A row in the tmnxDot1agCfmSapMipTable indicates that the
        specified SAP may have a MIP created on the endpoint."
    ::= { tmnxDot1agCfmMip 1 }

tmnxDot1agCfmSapMipEntry         OBJECT-TYPE
    SYNTAX     TmnxDot1agCfmSapMipEntry
    MAX-ACCESS not-accessible
    STATUS     current
    DESCRIPTION
       "The MIP (SAP) entry"
    INDEX { tmnxDot1agCfmSapMipIfIndex,
            tmnxDot1agCfmSapMipVlanIdOrNone,
            tmnxDot1agCfmSapMipPrimaryVlanId
          }
    ::= { tmnxDot1agCfmSapMipTable 1 }

TmnxDot1agCfmSapMipEntry         ::= SEQUENCE {
    tmnxDot1agCfmSapMipIfIndex        InterfaceIndex,
    tmnxDot1agCfmSapMipVlanIdOrNone   Unsigned32,
    tmnxDot1agCfmSapMipRowStatus      RowStatus,
    tmnxDot1agCfmSapMipSrcMacAddress  MacAddress,
    tmnxDot1agCfmSapMipPrimaryVlanId  VlanIdOrNone
}

tmnxDot1agCfmSapMipIfIndex       OBJECT-TYPE
    SYNTAX     InterfaceIndex
    MAX-ACCESS not-accessible
    STATUS     current
    DESCRIPTION
       "This object represents the  Bridge Port or aggregated port
        on which MEPs or MHFs might be configured."
    ::= { tmnxDot1agCfmSapMipEntry 1 }

tmnxDot1agCfmSapMipVlanIdOrNone  OBJECT-TYPE
    SYNTAX     Unsigned32
    MAX-ACCESS not-accessible
    STATUS     current
    DESCRIPTION
       "VLAN ID to which the MIP is attached, or 0, if none."
    ::= { tmnxDot1agCfmSapMipEntry 2 }

tmnxDot1agCfmSapMipRowStatus     OBJECT-TYPE
    SYNTAX     RowStatus
    MAX-ACCESS read-create
    STATUS     current
    DESCRIPTION
       "The tmnxDot1agCfmSapMipRowStatus specifies the ability to enable MIP
        creation under a SAP. Existing MIPs associated with the SAP may be
        viewed via the tmnxDot1agCfmStackTable."
    ::= { tmnxDot1agCfmSapMipEntry 3 }

tmnxDot1agCfmSapMipSrcMacAddress OBJECT-TYPE
    SYNTAX      MacAddress
    MAX-ACCESS  read-create
    STATUS      current
    DESCRIPTION
        "The value of tmnxDot1agCfmSapMipSrcMacAddress specifies the source
         MAC address used by the MIP.

         By default, the MAC address is the MAC address of the SAP."
    ::= { tmnxDot1agCfmSapMipEntry 4 }

tmnxDot1agCfmSapMipPrimaryVlanId OBJECT-TYPE
    SYNTAX      VlanIdOrNone
    MAX-ACCESS  not-accessible
    STATUS      current
    DESCRIPTION
        "The value of tmnxDot1agCfmSapMipPrimaryVlanId specifies primary VLAN ID
         used by the MIP. A value of zero '(0)' specifies a non-primary vlan
         MIP."
    ::= { tmnxDot1agCfmSapMipEntry 5 }


--
-- ******************************************************************
-- The MIP (SDP) Table
-- ******************************************************************
--
tmnxDot1agCfmSdpMipTable         OBJECT-TYPE
    SYNTAX     SEQUENCE OF TmnxDot1agCfmSdpMipEntry
    MAX-ACCESS not-accessible
    STATUS     current
    DESCRIPTION
       "A row in the tmnxDot1agCfmSdpMipTable indicates that the
        specified SDP-Binding may have a MIP created on the endpoint."
    ::= { tmnxDot1agCfmMip 2 }

tmnxDot1agCfmSdpMipEntry         OBJECT-TYPE
    SYNTAX     TmnxDot1agCfmSdpMipEntry
    MAX-ACCESS not-accessible
    STATUS     current
    DESCRIPTION
       "The MIP (SDP-Binding) entry"
    INDEX { tmnxDot1agCfmSdpMipSvcId,
            tmnxDot1agCfmSdpMipSdpId,
            tmnxDot1agCfmSdpMipVcId
          }
    ::= { tmnxDot1agCfmSdpMipTable 1 }

TmnxDot1agCfmSdpMipEntry         ::= SEQUENCE {
      tmnxDot1agCfmSdpMipSvcId           TmnxServId,
      tmnxDot1agCfmSdpMipSdpId           SdpId,
      tmnxDot1agCfmSdpMipVcId            Unsigned32,
      tmnxDot1agCfmSdpMipRowStatus       RowStatus,
      tmnxDot1agCfmSdpMipSrcMacAddress   MacAddress
    }

tmnxDot1agCfmSdpMipSvcId         OBJECT-TYPE
    SYNTAX     TmnxServId
    MAX-ACCESS not-accessible
    STATUS     current
    DESCRIPTION
       "The value of tmnxDot1agCfmSdpMipSvcId specifies the
        service on which the SDP-Binding MIP is configured."
    ::= { tmnxDot1agCfmSdpMipEntry 1 }

tmnxDot1agCfmSdpMipSdpId         OBJECT-TYPE
    SYNTAX     SdpId
    MAX-ACCESS not-accessible
    STATUS     current
    DESCRIPTION
       "The value of tmnxDot1agCfmSdpMipSdpId specifies the
        Bridge Port or aggregated port on which MEPs or MHFs
        might be configured."
    ::= { tmnxDot1agCfmSdpMipEntry 2 }

tmnxDot1agCfmSdpMipVcId          OBJECT-TYPE
    SYNTAX     Unsigned32
    MAX-ACCESS not-accessible
    STATUS     current
    DESCRIPTION
       "The value of tmnxDot1agCfmSdpMipVcId specifies, along with
        tmnxDot1agCfmSdpMipSdpId, the SDP Binding for the bridge."
    ::= { tmnxDot1agCfmSdpMipEntry 3 }

tmnxDot1agCfmSdpMipRowStatus     OBJECT-TYPE
    SYNTAX     RowStatus
    MAX-ACCESS read-create
    STATUS     current
    DESCRIPTION
       "The tmnxDot1agCfmSdpMipRowStatus specifies the ability to enable MIP
        creation under an SDP Binding. Existing MIPs associated with the SDP may
        be viewed via the tmnxDot1agCfmSdpBindStackTable."
    ::= { tmnxDot1agCfmSdpMipEntry 4 }

tmnxDot1agCfmSdpMipSrcMacAddress OBJECT-TYPE
    SYNTAX      MacAddress
    MAX-ACCESS  read-create
    STATUS      current
    DESCRIPTION
        "The value of tmnxDot1agCfmSdpMipSrcMacAddress specifies the source
         MAC address used by the MIP.

         By default, the MAC address is the MAC address of the chassis."
    ::= { tmnxDot1agCfmSdpMipEntry 5 }

-- Nokia SROS product series CFM MD table
--
-- Augmentation of the standard IEEE8021-CFM-MIB dot1agCfmMdTable.
--
-- The CFM Maintenance Domain Table
--

tmnxDot1agCfmMdTable             OBJECT-TYPE
    SYNTAX     SEQUENCE OF TmnxDot1agCfmMdEntry
    MAX-ACCESS not-accessible
    STATUS     current
    DESCRIPTION
           "The tmnxDot1agCfmMdTable extends the functionality of the
            dot1agCfmMdTable for the SROS series systems."
    ::= { tmnxDot1agCfmMd 1 }

tmnxDot1agCfmMdEntry             OBJECT-TYPE
    SYNTAX     TmnxDot1agCfmMdEntry
    MAX-ACCESS not-accessible
    STATUS     current
    DESCRIPTION
        "The tmnxDot1agCfmMdEntry consists of the configuration objects
         used to enhance the Maintenance Domain functionality.

         Use of AUGMENTS clause implies a one-to-one dependent relationship
         between the base table, dot1agCfmMdTable, and the augmenting
         table, tmnxDot1agCfmMdTable. This in effect extends the
         dot1agCfmMdTable with additional columns.

         Creation (or deletion) of a row in the dot1agCfmMdTable results
         in the same fate for the row in the tmnxDot1agCfmMdTable."
    AUGMENTS { dot1agCfmMdEntry }
    ::= { tmnxDot1agCfmMdTable 1 }

TmnxDot1agCfmMdEntry             ::= SEQUENCE {
      tmnxDot1agCfmMdCreationOrigin    TmnxCreateOrigin
    }

tmnxDot1agCfmMdCreationOrigin    OBJECT-TYPE
    SYNTAX     TmnxCreateOrigin
    MAX-ACCESS read-only
    STATUS     current
    DESCRIPTION
        "The value of tmnxDot1agCfmMdCreationOrigin indicates the
         mechanism which created this CFM Maintenance Domain."
    ::= { tmnxDot1agCfmMdEntry 1 }


-- The CFM Default Maintenance Domain Table
tmnxDot1agCfmDfltMdDefMipLtrPrio OBJECT-TYPE
    SYNTAX     Integer32 (0..7)
    MAX-ACCESS read-only
    STATUS     current
    DESCRIPTION
        "The value of tmnxDot1agCfmDfltMdDefMipLtrPrio indicates at what
         priority the link-trace response frames should be transmitted for a MIP
         request, for each tmnxDot1agCfmDefaultMdEntry whose
         tmnxDot1agCfmDefaultMdMipLtrPrio object contains the value '-1'.

         This object defaults to, and only supports the value '7'."
--  DEFVAL { 7 }
    ::= { tmnxDot1agCfmDefaultMd 1 }

tmnxDot1agCfmDefaultMdTable      OBJECT-TYPE
    SYNTAX      SEQUENCE OF TmnxDot1agCfmDefaultMdEntry
    MAX-ACCESS  not-accessible
    STATUS      current
    DESCRIPTION
        "The tmnxDot1agCfmDefaultMdTable AUGMENTS the standard MIB table,
         dot1agCfmDefaultMdTable. This table is used to enhance the Default
         Maintenance Domain functionality for Ethernet Connectivity Fault
         Management (Eth-CFM)."
    ::= { tmnxDot1agCfmDefaultMd 2 }

tmnxDot1agCfmDefaultMdEntry         OBJECT-TYPE
    SYNTAX      TmnxDot1agCfmDefaultMdEntry
    MAX-ACCESS  not-accessible
    STATUS      current
    DESCRIPTION
        "The tmnxDot1agCfmDefaultMdEntry consists of the configuration objects
         used to enhance the Default Maintenance Domain functionality."
    AUGMENTS { dot1agCfmDefaultMdEntry }
    ::= { tmnxDot1agCfmDefaultMdTable 1 }

TmnxDot1agCfmDefaultMdEntry      ::= SEQUENCE {
    tmnxDot1agCfmDefaultMdMipLtrPrio Integer32
}

tmnxDot1agCfmDefaultMdMipLtrPrio OBJECT-TYPE
    SYNTAX     Integer32 (-1 | 0..7)
    MAX-ACCESS read-write
    STATUS     current
    DESCRIPTION
        "The value of tmnxDot1agCfmDefaultMdMipLtrPrio specifies at what
         priority the link-trace response frames should be transmitted for a MIP
         request.

         If this object has the value '-1', the priority of this entry is deferred
         to tmnxDot1agCfmDfltMdDefMipLtrPrio."
    DEFVAL { -1 }
    ::= { tmnxDot1agCfmDefaultMdEntry  1 }

--
-- Notification Objects
--

tmnxDot1agCfmNotifySvcId         OBJECT-TYPE
    SYNTAX      TmnxServId
    MAX-ACCESS  accessible-for-notify
    STATUS      current
    DESCRIPTION
        "The tmnxDot1agCfmNotifySvcId is used in notifications when a row
         consisting of the service identifier may not exist when the trap
         is issued."
    ::= { tmnxDot1agCfmNotificationObjs 1 }


tmnxDot1agCfmMepFcltyType    OBJECT-TYPE
    SYNTAX      TmnxDot1agCfmMepFclty 
    MAX-ACCESS  accessible-for-notify
    STATUS      current
    DESCRIPTION
        "The value of tmnxDot1agCfmMepFcltyType indicates the type of 
         facility that a facility MEP has affected via a raised or cleared
         event.
         "
    ::= { tmnxDot1agCfmNotificationObjs 2 }


tmnxDot1agCfmMepFcltyInstance    OBJECT-TYPE
    SYNTAX      DisplayString
    MAX-ACCESS  accessible-for-notify
    STATUS      current
    DESCRIPTION
        "The value of tmnxDot1agCfmMepFcltyInstance indicates the specific
         facility instance that a facility MEP has affected via a raised
         or cleared event.

         This value is used in combination with its tmnxDot1agCfmMepFcltyType.

         The possible facility types and instance forms are described in the
         following table:

               Facility Type         |  Facility Instance
             ---------------------------------------------
               port                  |  slot/mda/port
               lag                   |  lag-id
               networkInterface      |  interface-name 
               qinqPortTunnelSap     |  sap-id
               qinqLagTunnelSap      |  sap-id
    
         The combined value will appear as in the following examples:
            port 7/2/2
            lag 1
            networkInterface test 
            qinqPortTunnelSap 2/2/2:100.*
            qinqLagTunnelSap lag-1:100.*

          When a facility fault occurs on a QinQ port or lag, the sap executing
          the CFM functional test, the sap will be included as part of the
          event log message.  However, QinQ facility tunnel MEPs on the sap are
          only the detection point for the defect / clear condition.  The QinQ
          facility tunnel is port or lag based and a representative outer tag. 
         "
    ::= { tmnxDot1agCfmNotificationObjs 3 }

--
-- Notifications
--

tmnxDot1agCfmMepLbmTestComplete  NOTIFICATION-TYPE
    OBJECTS {
              dot1agCfmMepTransmitLbmDestMacAddress
            }
    STATUS     current
    DESCRIPTION
       "The tmnxDot1agCfmMepLbmTestComplete notification indicates that
        a loopback test has been issued and results are ready."
    ::= { tmnxDot1agNotifications 1 }

tmnxDot1agCfmMepLtmTestComplete  NOTIFICATION-TYPE
    OBJECTS {
              dot1agCfmMepTransmitLtmSeqNumber
            }
    STATUS     current
    DESCRIPTION
       "The tmnxDot1agCfmMepLtmTestComplete notification indicates that
        a linktrace test has been issued and results are ready. The
        dot1agCfmMepTransmitLtmSeqNumber indicates the Transaction
        Identifier to use to retrieve the Link-trace results."
    ::= { tmnxDot1agNotifications 2 }

tmnxDot1agCfmMepEthTestComplete  NOTIFICATION-TYPE
    OBJECTS {
              tmnxDot1agCfmMepCurrByteCount,
              tmnxDot1agCfmMepCurrFailedBits,
              tmnxDot1agCfmMepCurrCrcFailures
            }
    STATUS     current
    DESCRIPTION
        "The tmnxDot1agCfmMepEthTestComplete notification indicates that
        an eth-test has been issued and results are ready. The
        tmnxDot1agCfmMepCurrByteCount indicates the number of bytes contained in
        the frame's Test TLV, and the tmnxDot1agCfmMepCurrFailedBits and
        tmnxDot1agCfmMepCurrCrcFailures indicate the failure state of the
        test. A value of Zero (0) for tmnxDot1agCfmMepCurrFailedBits and a
        value of 'false (2)' for tmnxDot1agCfmMepCurrCrcFailures indicates
        a successful test."
    ::= { tmnxDot1agNotifications 3 }

tmnxDot1agCfmMepDMTestComplete   NOTIFICATION-TYPE
    OBJECTS {
              tmnxDot1agCfmMepDelayTestDelay
            }
    STATUS     current
    DESCRIPTION
        "The tmnxDot1agCfmMepDMTestComplete notification indicates that a
        One-Way-Delay-Test (OWDT) frame, or a Two-Way-Delay-Test (TWDT) response
        was received. For an OWDT frame, traps are raised only when a delay
        threshold of three seconds is exceeded."
    ::= { tmnxDot1agNotifications 4 }

tmnxDot1agCfmMepAisStateChanged  NOTIFICATION-TYPE
    OBJECTS {
               tmnxDot1agCfmMepEthRxAis
            }
    STATUS     current
    DESCRIPTION
        "The tmnxDot1agCfmMepAisStateChanged notification is generated when
         a MEP enters or exits an AIS state."
    ::= { tmnxDot1agNotifications 5 }

tmnxDot1agCfmMipEvaluation       NOTIFICATION-TYPE
    OBJECTS {
               tmnxDot1agCfmNotifySvcId
            }
    STATUS  current
    DESCRIPTION
        "The tmnxDot1agCfmMipEvaluation notification is generated when a
         virtual MEP is created or deleted causing MIP reevaluation on the
         service. On virtual MEP creation, any MIPs in the service will be
          removed.  On virtual MEP deletion, the MIPs are reevaluated."
    ::= { tmnxDot1agNotifications 6 }

tmnxDot1agCfmMepSLMTestComplete  NOTIFICATION-TYPE
    OBJECTS {
               tmnxDot1agCfmMepSlmTestId,
               tmnxDot1agCfmMepSlmRemoteMepId,
               tmnxDot1agCfmMepSlmLastTxSeqF,
               tmnxDot1agCfmMepSlmPacketIn,
               tmnxDot1agCfmMepSlmPacketLossIn,
               tmnxDot1agCfmMepSlmPacketLossOut,
               tmnxDot1agCfmMepSlmPacketUnack
            }
    STATUS      current
    DESCRIPTION
        "The tmnxDot1agCfmMepSLMTestComplete notification is generated when
         a two-way Synthetic Loss Measurement (SLM) test is completed."
    ::= { tmnxDot1agNotifications 7 }

tmnxDot1agCfmMepCsfStateChanged  NOTIFICATION-TYPE
    OBJECTS {
               tmnxDot1agCfmMepCsfRxState
            }
    STATUS     current
    DESCRIPTION
        "The tmnxDot1agCfmMepCsfStateChanged notification is generated when
         a MEP enters or exits a CSF state."
    ::= { tmnxDot1agNotifications 8 }


tmnxDot1agCfmMepFcltyFaultRaise  NOTIFICATION-TYPE
    OBJECTS {
               tmnxDot1agCfmMepFcltyType,
               tmnxDot1agCfmMepFcltyInstance
            }
    STATUS     current
    DESCRIPTION
        "[CAUSE] The tmnxDot1agCfmMepFcltyFaultRaise notification is generated
         when the associated facility MEP dot1agCfmMepHighestPrDefect has
         increased.

         [EFFECT] This notification can be used to correlate the ETH_CFM
         dot1agCfmFaultAlarm event and the related IF-MIB::linkDown 
         notification caused by the failure of the facility MEP.

         [RECOVERY] Follow the recovery for the dot1agCfmFaultAlarm and 
         the related IF-MIB::linkDown caused by the failure of the 
         facility MEP."
    ::= { tmnxDot1agNotifications 9 }

tmnxDot1agCfmMepFcltyFaultClear  NOTIFICATION-TYPE
    OBJECTS {
               tmnxDot1agCfmMepFcltyType,
               tmnxDot1agCfmMepFcltyInstance
            }
    STATUS     current
    DESCRIPTION
        "[CAUSE] The tmnxDot1agCfmMepFcltyFaultClear notification is generated
         when the associated facility MEP has cleared an event affecting
         the specific tmnxDot1agCfmMepFcltyType tmnxDot1agCfmMepFcltyInstance
         combination over which it is configured.

         [EFFECT] This notification can be used to correlate the ETH_CFM
         dot1agCfmFaultAlarm event and the related IF-MIB::linkUp notification 
         caused by the facility MEP."
    ::= { tmnxDot1agNotifications 10 }

--
-- Conformance Information
--

tmnxDot1agCfmCompliances OBJECT IDENTIFIER ::= { tmnxDot1agMIBConformance 1 }
tmnxDot1agCfmGroups      OBJECT IDENTIFIER ::= { tmnxDot1agMIBConformance 2 }

-- Compliance statements

tmnxDot1agCfmCompliance          MODULE-COMPLIANCE
    STATUS     obsolete
    DESCRIPTION
       "The compliance statement for revision 1.0 of TIMETRA-IEEE8021-CFM-MIB."
    MODULE -- this module
        MANDATORY-GROUPS {
           tmnxDot1agCfmSdpBindStackGroup,
           tmnxDot1agCfmMepGroup,
           tmnxDot1agCfmSapStackGroup
        }
    ::= { tmnxDot1agCfmCompliances 1 }

tmnxDot1agCfmComplianceV7v0      MODULE-COMPLIANCE
    STATUS    obsolete
    DESCRIPTION
       "The compliance statement for revision 7.0 of the SROS system"
    MODULE -- this module
        MANDATORY-GROUPS {
           tmnxDot1agCfmSdpBindStackGroup,
           tmnxDot1agCfmSapStackGroup,
           tmnxDot1agCfmNotificationGroup,
           tmnxY1731CfmNotificationGroup,
           tmnxDot1agCfmMipGroup,
           tmnxDot1agCfmMipNotifyGroup,
           tmnxDot1agCfmMepGroupV7v0
        }
    ::= { tmnxDot1agCfmCompliances 2 }

tmnxDot1agCfmComplianceV8v0      MODULE-COMPLIANCE
    STATUS     obsolete
    DESCRIPTION
       "The compliance statement for revision 8.0 of the SROS system"
    MODULE -- this module
        MANDATORY-GROUPS {
           tmnxDot1agCfmSdpBindStackGroup,
           tmnxDot1agCfmSapStackGroup,
           tmnxDot1agCfmNotificationGroup,
           tmnxY1731CfmNotificationGroup,
           tmnxDot1agCfmMipNotifyGroup,
           tmnxDot1agCfmMipGroupV8v0,
           tmnxDot1agCfmMepGroupV7v0,
           tmnxDot1agCfmMepGroupV8v0
        }
    ::= { tmnxDot1agCfmCompliances 3 }

tmnxDot1agCfmComplianceV9v0      MODULE-COMPLIANCE
    STATUS     obsolete
    DESCRIPTION
       "The compliance statement for revision 9.0 of the SROS system"
    MODULE
        MANDATORY-GROUPS {
           tmnxDot1agCfmMaGroupV9v0,
           tmnxDot1agCfmSdpBindStackGroup,
           tmnxDot1agCfmSapStackGroup,
           tmnxDot1agCfmNotificationGroup,
           tmnxY1731CfmNotificationGroup,
           tmnxDot1agCfmMipNotifyGroup,
           tmnxDot1agCfmMipGroupV8v0,
           tmnxDot1agCfmMepGroupV7v0,
           tmnxDot1agCfmMepGroupV8v0,
           tmnxDot1agCfmMepGroupV9v0,
           tmnxDot1agCfmGlobalGroupV9v0,
           tmnxDot1agCfmMepSlmGroupV9v0,
           tmnxDot1agCfmMepSlmNotifyGroup,
           tmnxDot1agCfmMepMcastLbmGroup
        }
    ::= { tmnxDot1agCfmCompliances 4 }

tmnxDot1agCfmComplianceV10v0     MODULE-COMPLIANCE
    STATUS     obsolete
    DESCRIPTION
       "The compliance statement for revision 10.0 of the SROS system"
    MODULE -- this module
        MANDATORY-GROUPS {
           tmnxDot1agCfmGlobalGroupV9v0,
           tmnxDot1agCfmMaGroupV9v0,
           tmnxDot1agCfmMaGroupV10v0,
           tmnxDot1agCfmMepGroupV7v0,
           tmnxDot1agCfmMepGroupV8v0,
           tmnxDot1agCfmMepGroupV9v0,
           tmnxDot1agCfmMepGroupV10v0,
           tmnxDot1agCfmMepMcastLbmGroup,
           tmnxDot1agCfmMepSlmGroupV9v0,
           tmnxDot1agCfmMepSlmNotifyGroup,
           tmnxDot1agCfmMepSlmTWGroupV10v0,
           tmnxDot1agCfmMipGroupV8v0,
           tmnxDot1agCfmMipNotifyGroup,
           tmnxDot1agCfmNotificationGroup,
           tmnxDot1agCfmSapStackGroup,
           tmnxDot1agCfmSdpBindStackGroup,
           tmnxDot1agCfmStatsGroupV10v0,
           tmnxY1731CfmNotificationGroup,
           tmnxDot1agCfmGPGroupV10v0
        }
    ::= { tmnxDot1agCfmCompliances 5 }

tmnxDot1agCfmComplianceV11v0     MODULE-COMPLIANCE
    STATUS     obsolete
    DESCRIPTION
       "The compliance statement for revision 11.0 of the SROS system"
    MODULE -- this module
        MANDATORY-GROUPS {
           tmnxDot1agCfmGlobalGroupV9v0,
           tmnxDot1agCfmMaGroupV9v0,
           tmnxDot1agCfmMaGroupV10v0,
           tmnxDot1agCfmMaGroupV11v0,
           tmnxDot1agCfmMepGroupV7v0,
           tmnxDot1agCfmMepGroupV8v0,
           tmnxDot1agCfmMepGroupV9v0,
           tmnxDot1agCfmMepGroupV10v0,
           tmnxDot1agCfmMepCSFGroupV11v0,
           tmnxDot1agCfmMepMcastLbmGroup,
           tmnxDot1agCfmMepSlmGroupV9v0,
           tmnxDot1agCfmMepSlmNotifyGroup,
           tmnxDot1agCfmMepSlmTWGroupV10v0,
           tmnxDot1agCfmMipGroupV8v0,
           tmnxDot1agCfmMipNotifyGroup,
           tmnxDot1agCfmNotificationGroup,
           tmnxDot1agCfmCSFNotifyGroupV11v0,
           tmnxDot1agCfmSapStackGroup,
           tmnxDot1agCfmSdpBindStackGroup,
           tmnxDot1agCfmStatsGroupV10v0,
           tmnxY1731CfmNotificationGroup,
           tmnxDot1agCfmGPGroupV10v0,
           tmnxDot1agCfmMEPMgmtGroupV11v0,
           tmnxDot1agCfmMdGroupV11v0
        }
    ::= { tmnxDot1agCfmCompliances 6 }

tmnxDot1agCfmComplianceV12v0     MODULE-COMPLIANCE
    STATUS     current
    DESCRIPTION
       "The compliance statement for revision 12.0 of the SROS system"
    MODULE -- this module
        MANDATORY-GROUPS {
           tmnxDot1agCfmGlobalGroupV9v0,
           tmnxDot1agCfmMaGroupV9v0,
           tmnxDot1agCfmMaGroupV10v0,
           tmnxDot1agCfmMaGroupV11v0,
           tmnxDot1agCfmMaGroupV12v0,
           tmnxDot1agCfmMepGroupV7v0,
           tmnxDot1agCfmMepGroupV8v0,
           tmnxDot1agCfmMepGroupV9v0,
           tmnxDot1agCfmMepGroupV10v0,
           tmnxDot1agCfmMepCSFGroupV11v0,
           tmnxDot1agCfmMepGroupV12v0,
           tmnxDot1agCfmMepMcastLbmGroup,
           tmnxDot1agCfmMepSlmGroupV9v0,
           tmnxDot1agCfmMepSlmNotifyGroup,
           tmnxDot1agCfmMepSlmTWGroupV10v0,
           tmnxDot1agCfmMipGroupV8v0,
           tmnxDot1agCfmMipNotifyGroup,
           tmnxDot1agCfmNotificationGroup,
           tmnxDot1agCfmCSFNotifyGroupV11v0,
           tmnxDot1agCfmSapStackGroup,
           tmnxDot1agCfmSdpBindStackGroup,
           tmnxDot1agCfmStatsGroupV10v0,
           tmnxDot1agCfmStatsGroupV12v0,
           tmnxY1731CfmNotificationGroup,
           tmnxDot1agCfmGPGroupV10v0,
           tmnxDot1agCfmMEPMgmtGroupV11v0,
           tmnxDot1agCfmMdGroupV11v0,
           tmnxDot1agCfmScalarsGroupV12v0
        }
    ::= { tmnxDot1agCfmCompliances 7 }

tmnxDot1agCfmComplianceV13v0     MODULE-COMPLIANCE
    STATUS     current
    DESCRIPTION
        "The compliance statement for the object groups added in SROS Release
         13.0."
    MODULE -- this module
        MANDATORY-GROUPS {
            tmnxDot1agCfmMepGroupV13v0,
            tmnxDot1agCfmXmppEnhGroup
        }
    ::= { tmnxDot1agCfmCompliances 8 }

tmnxDot1agCfmComplianceV14v0     MODULE-COMPLIANCE
    STATUS     current
    DESCRIPTION
        "The compliance statement for the management of Ethernet Connectivity
         Fault Management (Eth-CFM) for release 14.0 on Nokia SROS
         series systems."
    MODULE -- this module
        MANDATORY-GROUPS {
            tmnxDot1agCfmDefaultMdGroupV14v0,
            tmnxDot1agNotifyObjsGroupV14v0,
            tmnxDot1agCfmCLENotifyGroupV14v0
        }
    ::= { tmnxDot1agCfmCompliances 9 }
-- Object Group statements

tmnxDot1agCfmSdpBindStackGroup   OBJECT-GROUP
    OBJECTS  {
        tmnxDot1agCfmSdpBindStackMdIndex,
        tmnxDot1agCfmSdpBindStackMaIndex,
        tmnxDot1agCfmSdpBindStackMepId,
        tmnxDot1agCfmSdpBindStackMacAddress
    }
    STATUS     current
    DESCRIPTION
       "The group of objects for management of dot1ag Stack Table applicable
        to implementing SDP-Bindings."
    ::= { tmnxDot1agCfmGroups 1 }

tmnxDot1agCfmMepGroup            OBJECT-GROUP
    OBJECTS {
        tmnxDot1agCfmMepSdpId,
        tmnxDot1agCfmMepVcId,
        tmnxDot1agCfmMepMacAddress
    }
    STATUS     obsolete
    DESCRIPTION
       "The group of objects for management of dot1ag MEP Table applicable
        to implementing SDP-Bindings."
    ::= { tmnxDot1agCfmGroups 2 }

tmnxDot1agCfmSapStackGroup       OBJECT-GROUP
    OBJECTS {
        tmnxDot1agCfmStackMdIndex,
        tmnxDot1agCfmStackMaIndex,
        tmnxDot1agCfmStackMepId,
        tmnxDot1agCfmStackMacAddress
    }
    STATUS     current
    DESCRIPTION
       "The group of objects for management of dot1ag Stack Table applicable
        to implementing SAP on the SROS."
    ::= { tmnxDot1agCfmGroups 3 }

tmnxDot1agCfmNotificationGroup   NOTIFICATION-GROUP
    NOTIFICATIONS {
        tmnxDot1agCfmMepLbmTestComplete,
        tmnxDot1agCfmMepLtmTestComplete
    }
    STATUS     current
    DESCRIPTION
       "The group of objects for management of dot1ag Notifications applicable
        to implementing CFM on the SROS."
    ::= {tmnxDot1agCfmGroups 4 }

tmnxDot1agCfmMipGroup            OBJECT-GROUP
    OBJECTS {
        tmnxDot1agCfmSapMipRowStatus,
        tmnxDot1agCfmSdpMipRowStatus
    }
    STATUS     obsolete
    DESCRIPTION
       "The group of objects for management of dot1ag MIP Tables applicable
        to implementing MIPs."
    ::= { tmnxDot1agCfmGroups 5 }

tmnxDot1agCfmMepGroupV7v0        OBJECT-GROUP
    OBJECTS {
        tmnxDot1agCfmMepSdpId,
        tmnxDot1agCfmMepVcId,
        tmnxDot1agCfmMepMacAddress,
        tmnxDot1agCfmMepAisEnable,
        tmnxDot1agCfmMepAisMegLevel,
        tmnxDot1agCfmMepAisPriority,
        tmnxDot1agCfmMepAisInterval,
        tmnxDot1agCfmMepEthTestEnable,
        tmnxDot1agCfmMepEthTestPattern,
        tmnxDot1agCfmMepEthRxAisInterval,
        tmnxDot1agCfmMepEthRxAis,
        tmnxDot1agCfmMepEthAisTxCount,
        tmnxDot1agCfmMepEthTestMacAddr,
        tmnxDot1agCfmMepEthTestDataLen,
        tmnxDot1agCfmMepEthTestPriority,
        tmnxDot1agCfmMepOWDTMacAddress,
        tmnxDot1agCfmMepOWDTPriority,
        tmnxDot1agCfmMepTWDTMacAddress,
        tmnxDot1agCfmMepTWDTPriority,
        tmnxDot1agCfmMepFrameCount,
        tmnxDot1agCfmMepByteCount,
        tmnxDot1agCfmMepFailedBits,
        tmnxDot1agCfmMepCrcFailures,
        tmnxDot1agCfmMepCurrByteCount,
        tmnxDot1agCfmMepCurrFailedBits,
        tmnxDot1agCfmMepCurrCrcFailures,
        tmnxDot1agCfmMepDelayTestDelay,
        tmnxDot1agCfmMepDelayVariation,
        tmnxDot1agCfmMepSvcId,
        tmnxDot1agCfmMepControlMep,
        tmnxDot1agCfmMepEthTestThreshold,
        tmnxDot1agCfmMepOWDTThreshold,
        tmnxDot1agCfmVStackMdIndex,
        tmnxDot1agCfmVStackMaIndex,
        tmnxDot1agCfmVStackMepId,
        tmnxDot1agCfmVStackMacAddress,
        tmnxDot1agCfmStackMPType
    }
    STATUS     current
    DESCRIPTION
        "The group of objects for managing dot1ag and Y.1731 tables applicable
         to Virtual MEPs and MEGs on SROS R7.0, and enabling APS support."
    ::= { tmnxDot1agCfmGroups 6 }

tmnxY1731CfmNotificationGroup    NOTIFICATION-GROUP
    NOTIFICATIONS {
        tmnxDot1agCfmMepEthTestComplete,
        tmnxDot1agCfmMepDMTestComplete,
        tmnxDot1agCfmMepAisStateChanged
    }
    STATUS     current
    DESCRIPTION
       "The group of objects for management of Y.1731 Notifications applicable
        to implementing CFM on the SROS."
    ::= {tmnxDot1agCfmGroups 7 }

tmnxDot1agCfmNotifyObjsGroup     OBJECT-GROUP
    OBJECTS {
        tmnxDot1agCfmNotifySvcId
    }
    STATUS      current
    DESCRIPTION
        "The group of objects supporting notifications for revision 7.0 on
         Nokia SROS series systems."
    ::= { tmnxDot1agCfmGroups 8 }

tmnxDot1agCfmMipNotifyGroup      NOTIFICATION-GROUP
    NOTIFICATIONS {
        tmnxDot1agCfmMipEvaluation
    }
    STATUS     current
    DESCRIPTION
        "The group of notification objects for management of dot1ag MIPs."
    ::= { tmnxDot1agCfmGroups 9 }

tmnxDot1agCfmV6v0Groups OBJECT IDENTIFIER ::= { tmnxDot1agCfmGroups 10 }
tmnxDot1agCfmV7v0Groups OBJECT IDENTIFIER ::= { tmnxDot1agCfmGroups 11 }
tmnxDot1agCfmV8v0Groups OBJECT IDENTIFIER ::= { tmnxDot1agCfmGroups 12 }

tmnxDot1agCfmMipGroupV8v0        OBJECT-GROUP
    OBJECTS {
        tmnxDot1agCfmSapMipRowStatus,
        tmnxDot1agCfmSapMipSrcMacAddress,
        tmnxDot1agCfmSdpMipRowStatus,
        tmnxDot1agCfmSdpMipSrcMacAddress
    }
    STATUS     current
    DESCRIPTION
       "The group of objects for management of dot1ag MIP Tables applicable
        to implementing MIPs for SROS release 8.0."
    ::= { tmnxDot1agCfmV8v0Groups 1 }

tmnxDot1agCfmMepGroupV8v0        OBJECT-GROUP
    OBJECTS {
        tmnxDot1agCfmMepFaultPropagation
    }
    STATUS     current
    DESCRIPTION
        "The group of objects for managing dot1ag and Y.1731 tables applicable
         to Virtual MEPs and MEGs on SROS R8.0, and enabling APS support."
    ::= { tmnxDot1agCfmV8v0Groups 2 }

tmnxDot1agCfmV9v0Groups OBJECT IDENTIFIER ::= { tmnxDot1agCfmGroups 13 }

tmnxDot1agCfmMaGroupV9v0         OBJECT-GROUP
    OBJECTS {
        tmnxDot1agCfmMaNetHoldDownTimer
    }
    STATUS      current
    DESCRIPTION
        "The group of objects for management of dot1ag and Y.1731 tables
         applicable to enhancing Maintenance Associations for the SROS
         release 9.0."
    ::= { tmnxDot1agCfmV9v0Groups 1 }

tmnxDot1agCfmMepGroupV9v0        OBJECT-GROUP
    OBJECTS {
        tmnxDot1agCfmMepFacilityIfIndex,
        tmnxDot1agCfmMepFacilityVlanId,
        tmnxDot1agCfmMepFacilityType,
        tmnxDot1agCfmMepFcltyFaultNotify,
        tmnxDot1agCfmMepDescription,
        tmnxDot1agCfmMepMcLagInactive
    }
    STATUS      current
    DESCRIPTION
        "The group of objects for management of dot1ag and Y.1731 tables
         applicable to implementing Facility MEPs for the SROS release 9.0."
    ::= { tmnxDot1agCfmV9v0Groups 2 }

tmnxDot1agCfmGlobalGroupV9v0     OBJECT-GROUP
    OBJECTS {
        tmnxDot1agCfmMcLagStdbyInactive,
        tmnxDot1agCfmMcLagPropHoldTime
    }
    STATUS      current
    DESCRIPTION
        "The group of global objects for enhancing dot1ag and Y.1731 features
         with support for Multi-Chassis LAG ports for the SROS release 9.0."
    ::= { tmnxDot1agCfmV9v0Groups 3 }

tmnxDot1agCfmMepSlmGroupV9v0     OBJECT-GROUP
    OBJECTS {
        tmnxDot1agCfmSLMInactivityTimer,
        tmnxDot1agCfmMepSlmTWTestStatus,
        tmnxDot1agCfmMepSlmTWTestId,
        tmnxDot1agCfmMepSlmTWMacAddress,
        tmnxDot1agCfmMepSlmTWPriority,
        tmnxDot1agCfmMepSlmTWInterval,
        tmnxDot1agCfmMepSlmTWTimeout,
        tmnxDot1agCfmMepSlmTWDataSize,
        tmnxDot1agCfmMepSlmTWSendCount,
        tmnxDot1agCfmMepSlmOWTestStatus,
        tmnxDot1agCfmMepSlmOWTestId,
        tmnxDot1agCfmMepSlmOWMacAddress,
        tmnxDot1agCfmMepSlmOWPriority,
        tmnxDot1agCfmMepSlmOWInterval,
        tmnxDot1agCfmMepSlmOWDataSize,
        tmnxDot1agCfmMepSlmOWSendCount,
        tmnxDot1agCfmMepSlmTestId,
        tmnxDot1agCfmMepSlmRemoteMepId,
        tmnxDot1agCfmMepSlmLastTxSeqF,
        tmnxDot1agCfmMepSlmPacketIn,
        tmnxDot1agCfmMepSlmPacketLossIn,
        tmnxDot1agCfmMepSlmPacketLossOut,
        tmnxDot1agCfmMepSlmPacketUnack
    }
    STATUS      current
    DESCRIPTION
        "The group of objects for management of Synthetic Loss Measurement Tests
         for the SROS release 9.0."
    ::= { tmnxDot1agCfmV9v0Groups 4 }

tmnxDot1agCfmMepSlmNotifyGroup   NOTIFICATION-GROUP
    NOTIFICATIONS {
        tmnxDot1agCfmMepSLMTestComplete
    }
    STATUS     current
    DESCRIPTION
        "The group of notification objects for management of dot1ag Synthetic
         Loss Measurement (SLM) test for the SROS release 9.0."
    ::= { tmnxDot1agCfmV9v0Groups 5 }

tmnxDot1agCfmMepMcastLbmGroup    OBJECT-GROUP
    OBJECTS {
        tmnxDot1agCfmMepLbmRxIndex
    }
    STATUS      current
    DESCRIPTION
        "The group of objects for management of multicast loopback tests for the
         SROS release 9.0."
    ::= { tmnxDot1agCfmV9v0Groups 6 }

tmnxDot1agCfmV10v0Groups OBJECT IDENTIFIER ::= { tmnxDot1agCfmGroups 14 }

tmnxDot1agCfmMepSlmTWGroupV10v0  OBJECT-GROUP
    OBJECTS {
        tmnxDot1agCfmMepSlmTWIntrvlUnits
    }
    STATUS      current
    DESCRIPTION
        "The group of objects providing additional management options for
         two-way SLM tests in SROS Release 10.0."
    ::= { tmnxDot1agCfmV10v0Groups 1 }

tmnxDot1agCfmMaGroupV10v0        OBJECT-GROUP
    OBJECTS {
        tmnxDot1agCfmMaMepListMacAddress,
        tmnxDot1agCfmMaNetTotalMEPCount
    }
    STATUS      current
    DESCRIPTION
        "The group of additional objects for management of dot1ag and Y.1731
         tables applicable to Maintenance Associations for the SROS
         release 10.0."
    ::=  { tmnxDot1agCfmV10v0Groups 2 }

tmnxDot1agCfmMepGroupV10v0       OBJECT-GROUP
    OBJECTS {
        tmnxDot1agCfmMepCcmPaddingSize,
        tmnxDot1agCfmMepCcmIgnoreTLVs,
        tmnxDot1agCfmMepAisLowPrioDef
    }
    STATUS      current
    DESCRIPTION
        "The group of additional objects for management of dot1ag and Y.1731
         tables applicable to MEPs for the SROS release 10.0."
    ::=  { tmnxDot1agCfmV10v0Groups 3 }

tmnxDot1agCfmStatsGroupV10v0     OBJECT-GROUP
    OBJECTS {
        tmnxDot1agCfmGlobalPacketRxCount,
        tmnxDot1agCfmGlobalPacketTxCount,
        tmnxDot1agCfmGlobalPacketDropped,
        tmnxDot1agCfmGlobalPacketDiscard,
        tmnxDot1agCfmCompName,
        tmnxDot1agCfmCompResourceUsage,
        tmnxDot1agCfmCompResourceLimit
    }
    STATUS      current
    DESCRIPTION
        "The group of objects reporting dot1ag and Y.1731 global statistics
         applicable for the SROS release 10.0."
    ::= { tmnxDot1agCfmV10v0Groups 4 }

tmnxDot1agCfmGPGroupV10v0        OBJECT-GROUP
    OBJECTS {
        tmnxDot1agCfmGraceTxEnable,
        tmnxDot1agCfmGracePeriod,
        tmnxDot1agCfmMepDbGraceRx
    }
    STATUS      current
    DESCRIPTION
        "The group of additional objects for management of dot1ag and Y.1731
        tables applicable to Continuity Check and the grace period
        notifications."
    ::= { tmnxDot1agCfmV10v0Groups 5 }

tmnxDot1agCfmV11v0Groups OBJECT IDENTIFIER ::= { tmnxDot1agCfmGroups 15 }

tmnxDot1agCfmMEPMgmtGroupV11v0   OBJECT-GROUP
    OBJECTS {
        tmnxDot1agCfmMepMgmtRowStatus,
        tmnxDot1agCfmMepMgmtType,
        tmnxDot1agCfmMepMgmtServiceId,
        tmnxDot1agCfmMepMgmtIfIndex,
        tmnxDot1agCfmMepMgmtPrimaryVid,
        tmnxDot1agCfmMepMgmtSdpId,
        tmnxDot1agCfmMepMgmtVcId,
        tmnxDot1agCfmMepMgmtFcltyIfIndex,
        tmnxDot1agCfmMepMgmtFcltyVlanId,
        tmnxDot1agCfmMepMgmtDirection,
        tmnxDot1agCfmPVStackMdIndex,
        tmnxDot1agCfmPVStackMaIndex,
        tmnxDot1agCfmPVStackMepId,
        tmnxDot1agCfmPVStackMacAddress
    }
    STATUS      current
    DESCRIPTION
        "The group of additional objects for management of dot1ag and Y.1731
         tables applicable to the row creation and deletion of MEPs."
    ::= { tmnxDot1agCfmV11v0Groups 1 }


tmnxDot1agCfmMaGroupV11v0        OBJECT-GROUP
    OBJECTS {
        tmnxDot1agCfmMaCompMipLtrPrio
    }
    STATUS      current
    DESCRIPTION
        "The group of additional objects for management of dot1ag and Y.1731
         tables applicable to the Maintenance Association (MA)."
    ::= { tmnxDot1agCfmV11v0Groups 2 }

tmnxDot1agCfmMdGroupV11v0        OBJECT-GROUP
    OBJECTS {
        tmnxDot1agCfmMdCreationOrigin
    }
    STATUS      current
    DESCRIPTION
        "The group of additional objects for management of dot1ag and Y.1731
         tables applicable to the Maintenance Domain (MD)."
    ::= { tmnxDot1agCfmV11v0Groups 3 }

tmnxDot1agCfmMepCSFGroupV11v0    OBJECT-GROUP
    OBJECTS {
        tmnxDot1agCfmMepCsfEnable,
        tmnxDot1agCfmMepCsfRxMultiplier,
        tmnxDot1agCfmMepCsfRxState,
        tmnxDot1agCfmMepCsfRxInterval,
        tmnxDot1agCfmMepCsfRxCount
    }
    STATUS      current
    DESCRIPTION
        "The group of additional objects for management of dot1ag and Y.1731 MEP
         tables for the purpose of processing CSF (Client Signal Fault) frames."
    ::= { tmnxDot1agCfmV11v0Groups 4 }

tmnxDot1agCfmCSFNotifyGroupV11v0 NOTIFICATION-GROUP
    NOTIFICATIONS {
        tmnxDot1agCfmMepCsfStateChanged
    }
    STATUS      current
    DESCRIPTION
        "The group of additional notifications for management of dot1ag and
         Y.1731 MEP tables for the purpose of processing CSF (Client Signal
         Fault) frames."
    ::= { tmnxDot1agCfmV11v0Groups 5 }

tmnxDot1agCfmV12v0Groups OBJECT IDENTIFIER ::= { tmnxDot1agCfmGroups 16 }

tmnxDot1agCfmMaGroupV12v0        OBJECT-GROUP
    OBJECTS {
        tmnxDot1agCfmMaNetAutoDiscAdmin,
        tmnxDot1agCfmMaMepListAutoDiscvd,
        tmnxDot1agCfmMaNetIdPermission
    }
    STATUS      current
    DESCRIPTION
        "The group of additional objects for management of dot1ag and Y.1731
         tables applicable to Maintenance Associations for the SROS
         release 12.0."
    ::=  { tmnxDot1agCfmV12v0Groups 1 }

tmnxDot1agCfmStatsGroupV12v0     OBJECT-GROUP
    OBJECTS {
        tmnxDot1agCfmGlobalOpcodeRx,
        tmnxDot1agCfmGlobalOpcodeTx,
        tmnxDot1agCfmGlobalAisTxActive,
        tmnxDot1agCfmGlobalAisTxFail
    }
    STATUS      current
    DESCRIPTION
        "The group of additional objects reporting dot1ag and Y.1731 global
         statistics applicable for the SROS release 12.0."
    ::= { tmnxDot1agCfmV12v0Groups 2 }

tmnxDot1agCfmMepGroupV12v0       OBJECT-GROUP
    OBJECTS {
        tmnxDot1agCfmMepOpcodeRx,
        tmnxDot1agCfmMepOpcodeTx,
        tmnxDot1agCfmMepEthAisTxFail,
        tmnxDot1agCfmMepTxLbmTimeout,
        tmnxDot1agCfmMepTxLbmInterval,
        tmnxDot1agCfmMepLbmPaddingSize,
        tmnxDot1agCfmMepIfSupportEnable
    }
    STATUS      current
    DESCRIPTION
        "The group of additional objects for management of dot1ag and Y.1731
         tables applicable to MEPs for the SROS release 12.0."
    ::=  { tmnxDot1agCfmV12v0Groups 3 }

tmnxDot1agCfmScalarsGroupV12v0   OBJECT-GROUP
    OBJECTS {
        tmnxDot1agCfmSenderIdType,
        tmnxDot1agCfmSenderIdName
    }
    STATUS      current
    DESCRIPTION
        "The group of additional objects for management of dot1ag and Y.1731
         global configuration for the SROS release 12.0."
    ::= { tmnxDot1agCfmV12v0Groups 4 }

tmnxDot1agCfmV13v0Groups OBJECT IDENTIFIER ::= { tmnxDot1agCfmGroups 17 }

tmnxDot1agCfmMepGroupV13v0       OBJECT-GROUP
    OBJECTS {
        tmnxDot1agCfmMepCollectLmmStats
    }
    STATUS      current
    DESCRIPTION
        "The group of additional objects for management of dot1ag and Y.1731 MEF
         tables for SROS release 13.0."
    ::=  { tmnxDot1agCfmV13v0Groups 1 }

tmnxDot1agCfmXmppEnhGroup  OBJECT-GROUP
    OBJECTS {
        tmnxDot1agCfmMepCreationOrigin
    }
    STATUS current
    DESCRIPTION
        "The group of additional objects for XMPP support for fully dynamic services
         for SROS release 13.0R4."
    ::= { tmnxDot1agCfmV13v0Groups 2 }

tmnxDot1agCfmV14v0Groups OBJECT IDENTIFIER ::= { tmnxDot1agCfmGroups 18 }

tmnxDot1agCfmDefaultMdGroupV14v0 OBJECT-GROUP
    OBJECTS {
        tmnxDot1agCfmDfltMdDefMipLtrPrio,
        tmnxDot1agCfmDefaultMdMipLtrPrio
    }
    STATUS      current
    DESCRIPTION
        "The group of additional objects maintaining the Default Maintenance
         Domain (MD) on Nokia SROS series systems for Release 14.0."
    ::= { tmnxDot1agCfmV14v0Groups 1 }


tmnxDot1agNotifyObjsGroupV14v0 OBJECT-GROUP
    OBJECTS {
        tmnxDot1agCfmMepFcltyType,
        tmnxDot1agCfmMepFcltyInstance
    }
    STATUS      current
    DESCRIPTION
        "The group of objects for management of CFM Facility MEP correlation
         log events for the SROS release 14.0."
    ::= { tmnxDot1agCfmV14v0Groups 2 }


tmnxDot1agCfmCLENotifyGroupV14v0 NOTIFICATION-GROUP
    NOTIFICATIONS {
        tmnxDot1agCfmMepFcltyFaultRaise,
        tmnxDot1agCfmMepFcltyFaultClear
    }
    STATUS     current
    DESCRIPTION
        "The group of notifications for management of the CFM Facility MEP
         correlation log events for the SROS release 14.0."
    ::= {tmnxDot1agCfmV14v0Groups 3 }
END

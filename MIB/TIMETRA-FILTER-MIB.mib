TIMETRA-FILTER-MIB DEFINITIONS ::= BEGIN

IMPORTS
    MODULE-IDENTITY, OBJECT-TYPE, NOTIFICATION-TYPE,
    Unsigned32, Integer32, IpAddress, Counter32, Counter64,
    Gauge32, TimeTicks, Opaque
        FROM SNMPv2-SMI

    MODULE-COMPLIANCE, OBJECT-GROUP, NOTIFICATION-GROUP
        FROM SNMPv2-CONF

    TEXTUAL-CONVENTION, RowStatus, MacAddress,
    TruthValue, DisplayString, TimeStamp,
    RowPointer
        FROM SNMPv2-TC

    timetraSRMIBModules, tmnxSRObjs, tmnxSRNotifyPrefix,
    tmnxSRConfs
        FROM TIMETRA-GLOBAL-MIB

    TmnxAdminState, TmnxOperState, TNamedItem,
    TNamedItemOrEmpty, Dot1PPriority, IpAddressPrefixLength,
    ServiceAccessPoint, TItemDescription, TDSCPNameOrEmpty,
    TDSCPFilterActionValue, TIpProtocol, TIpOption,
    TTcpUdpPort, TTcpUdpPortOperator, TFrameType,
    TmnxServId, TmnxPortID, TmnxEncapVal,
    SdpBindId, SvcISID, QTagFullRange,
    QTagFullRangeOrNone, TMacFilterType, TmnxVRtrID, TmnxVRtrIDOrZero,
    TLNamedItemOrEmpty, TRegularExpression, TmnxHttpRedirectUrl,
    IPv6FlowLabel, IPv6FlowLabelMask, TmnxVRtrMplsLspID, TmnxNatSubscriberType,
    TmnxNatSubscriberTypeOrNone, TOperator
        FROM TIMETRA-TC-MIB

    InetAddressIPv6,InetAddressPrefixLength, InetAddressType,
    InetAddress, InetAddressIPv4
        FROM INET-ADDRESS-MIB

    InterfaceIndexOrZero
        FROM IF-MIB
    ;

timetraFilterMIBModule MODULE-IDENTITY
        LAST-UPDATED "201601010000Z"
        ORGANIZATION "Nokia"
        CONTACT-INFO
            "Nokia SROS Support
             Web: http://www.nokia.com"
        DESCRIPTION
        "This document is the SNMP MIB module to manage and provision
         Filter features on Nokia SROS systems.

         Copyright 2003-2016 Nokia. All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive
         license to use and distribute an unmodified copy of this
         Specification in connection with management of Nokia
         products, and without fee, provided this copyright notice and
         license appear on all copies.

         This Specification is supplied 'as is', and Nokia
         makes no warranty, either express or implied, as to the use,
         operation, condition, or performance of the Specification."

--
-- Revision History
--
        REVISION        "201601010000Z"
        DESCRIPTION     "Rev 14.0                1 Jan 2016 00:00
                         14.0 release of the TIMETRA-FILTER-MIB."

        REVISION        "201501010000Z"
        DESCRIPTION     "Rev 13.0                1 Jan 2015 00:00
                         13.0 release of the TIMETRA-FILTER-MIB."

        REVISION        "201401010000Z"
        DESCRIPTION     "Rev 12.0                1 Jan 2014 00:00
                         12.0 release of the TIMETRA-FILTER-MIB."

        REVISION        "201208010000Z"
        DESCRIPTION     "Rev 11.0                1 Aug 2012 00:00
                         11.0 release of the TIMETRA-FILTER-MIB."

        REVISION        "201102010000Z"
        DESCRIPTION     "Rev 9.0                01 Feb 2011 00:00
                         9.0 release of the TIMETRA-FILTER-MIB."

        REVISION        "200907010000Z"
        DESCRIPTION     "Rev 8.0                01 Jul 2009 00:00
                         8.0 release of the TIMETRA-FILTER-MIB."

        REVISION        "200807010000Z"
        DESCRIPTION     "Rev 6.1                01 Jul 2008 00:00
                         6.1 release of the TIMETRA-FILTER-MIB."

        REVISION        "200801010000Z"
        DESCRIPTION     "Rev 6.0                01 Jan 2008 00:00
                         6.0 release of the TIMETRA-FILTER-MIB."

        REVISION        "200701010000Z"
        DESCRIPTION     "Rev 5.0                01 Jan 2007 00:00
                         5.0 release of the TIMETRA-FILTER-MIB."

        REVISION        "200602280000Z"
        DESCRIPTION     "Rev 4.0                28 Feb 2006 00:00
                         4.0 release of the TIMETRA-FILTER-MIB."

        REVISION        "200508310000Z"
        DESCRIPTION     "Rev 3.0                31 Aug 2005 00:00
                         3.0 release of the TIMETRA-FILTER-MIB."

        REVISION        "200501240000Z"
        DESCRIPTION     "Rev 2.1                24 Jan 2005 00:00
                         2.1 release of the TIMETRA-FILTER-MIB."

        REVISION        "200401150000Z"
        DESCRIPTION     "Rev 2.0                15 Jan 2004 00:00
                         2.0 release of the TIMETRA-FILTER-MIB."

        REVISION        "200308150000Z"
        DESCRIPTION     "Rev 1.2                15 Aug 2003 00:00
                         1.2 release of the TIMETRA-FILTER-MIB."

        REVISION        "200301290000Z"
        DESCRIPTION     "Rev 0.1                29 Jan 2003 00:00
                         Initial version of the TIMETRA-FILTER-MIB."

        ::= { timetraSRMIBModules 21 }

tFilterObjects             OBJECT IDENTIFIER ::= { tmnxSRObjs 21 }
tFilterNotificationsPrefix OBJECT IDENTIFIER ::= { tmnxSRNotifyPrefix 21 }
tFilterNotifications       OBJECT IDENTIFIER ::= { tFilterNotificationsPrefix 0 }
tFilterMIBConformance      OBJECT IDENTIFIER ::= { tmnxSRConfs 21 }

tFilterNotificationObjects OBJECT IDENTIFIER ::= { tFilterObjects 8 }
tFilterTimeStampObjects    OBJECT IDENTIFIER ::= { tFilterObjects 9 }

--
-- TEXTUAL-CONVENTIONs for Nokia SROS series Filter Elements
--

TFilterID ::= TEXTUAL-CONVENTION
    STATUS current
    DESCRIPTION
        "The identification number of a filter. 0 indicates an invalid
         filter-id."
    SYNTAX Unsigned32 (0..65535)

TIPFilterIdOrEmpty ::= TEXTUAL-CONVENTION
    STATUS current
    DESCRIPTION
        "The identification number of an IP filter."
    SYNTAX INTEGER (-1|0..65535)

TVsdFilterID ::= TEXTUAL-CONVENTION
    STATUS current
    DESCRIPTION
        "The identification number of a filter managed by a VSD controller.

         The value of the upper 16 bits is always equal to 0x0400.

         The value of the lower 16 bits corresponds to the last segment
         of the name used for the filter in CLI (_tmnx_vsd_<lower_16_bits>)."
    SYNTAX Unsigned32 (67108865..67174399)

TConfigOrVsdFilterID ::= TEXTUAL-CONVENTION
    STATUS current
    DESCRIPTION
        "The identification number of a filter. Any value greater than
         0x0000FFFF (65535) indicates a filter that was dynamically created
         (auto-generated) by the system and as such cannot be used as part
         of any SNMP SET operation.

         - The range 0x00000001 .. 0x0000FFFF (1 .. 65535)
           indicates a regular configuration originated filter.

         - The range 0x04000001 .. 0x0400FFFF (67108865 .. 67174399)
           indicates a filter managed by a VSD controller. In this case
           the last 16 bits indicate the ID of the VSD filter.

         - The value 0 indicates an invalid filter-id (e.g. no filter applied
           on a particular endpoint)."
    SYNTAX Unsigned32 (0..65535|67108865..67174399)

TAnyFilterID ::= TEXTUAL-CONVENTION
    STATUS current
    DESCRIPTION
        "Represents a filter Id.
         Any value greater than 65535 indicates a filter that was created
         (auto-generated) by the system.

         - The range 0x01000000 through 0x0100FFFF indicates a filter used for
           BGP Flow-Spec. In this case, the last 16 bits indicate the value of
           the vRtrID where the filter is active.

         - The range 0x03000000 through 0x0300FFFF indicates a filter used for
           Open-Flow.

         - The range 0x20000000 .. 0x3FFFFFFF is used for handling filter rules
           (received from RADIUS) that are to be shared between users. The Id
           is encoded as follows:
           - the highest 3 bits (0b001) indicate that it is an auto-generated
             shared filter
           - the subsequent 13 bits indicate which combination of filter rules
             are inserted; this corresponds to the second number in the filter
             Id as displayed in CLI: the '1' in the example '9:1'
           - the subsequent 16 bits indicate the base filter Id; this
             corresponds to the first number ('9') in  '9:1'

         - The range 0x10000000 .. 0x1FFFFFFF is used for handling filter
           flow-rules (received from DIAMETER) that are to be shared between
           users. The Id is encoded as follows:
           - the highest 4 bits (0b0001) indicate that it is an auto-generated
             flow-rule filter
           - the subsequent 12 bits indicate which combination of flow-rules are
             inserted; this corresponds to the second number in the filter Id as
             displayed in CLI: the '2' in the example '9:P2'
           - the subsequent 16 bits indicate the base filter Id; this
             corresponds to the first number ('9') in the example '9:P2'

         - The range 0x04000001 .. 0x0400FFFF (67108865..67174399)
           indicates a filter managed by a VSD controller. In this case
           the last 16 bits indicate the ID of the VSD filter.
           "
    SYNTAX Unsigned32

TFilterScope ::= TEXTUAL-CONVENTION
    STATUS current
    DESCRIPTION
        "This textual-convention determines some aspects of an item's
         behavior regarding creation and use, unused entry garbage collection,
         and automated promulgation by Element Management System to
         other systems in the service domain.

         TFilterScope is an extension of the textual-convention TItemScope.

         exclusive:

            When the scope of an item is defined as exclusive, the item can
            only be applied once, for example to a single SAP.  Attempting
            to assign the policy to a second SAP is not allowed and will
            result in an error.  If the item is removed from the exclusive
            SAP, it will become available for assignment to another
            exclusive SAP.

            A non-applied exclusive scope policy is a candidate to be removed
            from the system by a TBD garbage collection command.

            The system default policies cannot be put into the exclusive scope.
            An error will be generated if scope exclusive is executed in
            any policies with a policy-id equal to 1.

         template:

            When the scope of an item is defined as template, the item can be
            applied any number of times.  Policies with template scope
            will not be considered for deletion by a TBD garbage collection
            command; all items of scope 'template' must be deleted explicitly.

            The system default policies will always be scope template.
            An error will occur if a policy-id 1 is attempted to be
            set to scope exclusive.

         embedded:

            When the scope of a filter is defined as embedded, this indicates
            that the filter may be embedded in other non-embedded filters.
            An embedded filter may not be applied anywhere in the system.
            Attempting to set scope to embedded for a filter which is
            already applied will be rejected by the system.

         system:

            When the scope of a filter policy is defined as system, the filter
            policy can be used as a common system filter policy only.

            The policy cannot be applied directly anywhere in the system.
            In order to activate the policy it must be configured as the active
            system filter policy in tFilterSystemFilterTable.

            All other 'exclusive' and 'template' IP / IPv6 filter policies may
            be chained to the active system policy by setting the
            tIPFilterChainToSystemFilter or tIPv6FilterChainToSystemFilter
            object to 'true(1)'.

            When an IP / IPv6 filter policy is chained to the system filter
            policy, system filter policy's rules are executed first before
            any rules of the activating filter policy are executed.

            The scope of a filter policy can be set to/from this value only
            when the policy does not contain any entry."
    SYNTAX INTEGER { exclusive(1),
                     template(2),
                     embedded(3),
                     system(4)
                   }

TItemMatch ::= TEXTUAL-CONVENTION
    STATUS current
    DESCRIPTION
        "when set to off, the item is not matched.
         when set to false, packets without the item match the filter.
         when set to true, packets with the item match the filter."
    SYNTAX INTEGER { off(1), false(2), true(3) }

TEntryIndicator ::= TEXTUAL-CONVENTION
    STATUS current
    DESCRIPTION
        "Uniquely identifies an entry in a policy or filter table. The
         value 0 is not a valid entry-id. When used as insertion point
         the value 0 indicates that entries must be inserted at the very
         beginning, i.e.before the first entry defined."
    SYNTAX Unsigned32 (0..65535)

TEntryId ::= TEXTUAL-CONVENTION
    STATUS current
    DESCRIPTION
        "Uniquely identifies an entry in a policy or filter table.
         To facilitate insertion of entries in the tables, we recommend
         assigning entry IDs by 10s:  10, 20, 30, etc."
    SYNTAX TEntryIndicator (1..65535)

TAnyEntryId ::= TEXTUAL-CONVENTION
    STATUS current
    DESCRIPTION
        "Uniquely identifies an entry in a filter table.

         The values 1..65535 are available for user configuration.
         The range (65536 .. 671154175) is used internally by the system to map
         BGP flow spec generated filter entries."
    SYNTAX Unsigned32 (1..671154175)

TEntryIdOrZero ::= TEXTUAL-CONVENTION
    STATUS current
    DESCRIPTION
        "uniquely identifies an entry in a policy or filter table.
         to facilitate insertion of entries in the tables, we recommend
         assigning entry IDs by 10s:  10, 20, 30, etc.
         The value 0, means that the object does not refer to a filter
         entry at this time."
    SYNTAX TEntryIndicator (0..65535)
    
TEmbedInsrtEntryId ::= TEXTUAL-CONVENTION
    STATUS current
    DESCRIPTION
        "Uniquely indicates the position where the filter entry is or
        would be (inactive embedding) inserted when a configured
        or an auto-created filter is inserted in a filter with scope other
        than 'embedded'."
    SYNTAX Unsigned32 (1..131071)

TFilterAction ::= TEXTUAL-CONVENTION
    STATUS current
    DESCRIPTION
        "Action to take on a packet:
         - drop        (1): packets matching the filter entry are dropped.
         - forward     (2): packets matching the filter entry are forwarded.
         - httpRedirect(4): packets matching the filter entry are redirected.
         - nat         (5): packets matching the filter entry are forwarded to
                            the NAT function in the system.
         - reassemble  (6): packets matching the filter entry are forwarded to
                            the packet REASSEMBLE function in the system.
         - gtpLclBrkout(7): packets matching the filter entry are broken out
                            locally from a GTP tunnel (and thereby bypass the
                            mobile packet core). For packets that are not sent
                            in the context of a GTP tunnel, this action is
                            equivalent to 'forward'.
         - forwardEsiL2(8): packets matching the filter entry are forwarded to
                            ESI identified first appliance in Nuage service
                            chain using EVPN-resolved VXLAN tunnel in
                            the specified VPLS service.
         - forwardEsiL3(9): packets matching the filter entry are forwarded to
                            ESI/SF-IP identified first appliance in Nuage
                            service chain using EVPN-resolved VXLAN tunnel over
                            the configured VAS interface in the specified VPRN
                            service.
         - unrecognized(11):Tables tMacFilterParamsTable, tIPFilterParamsTable,
                            tIPv6FilterParamsTable and their augment tables can
                            only be used to configure actions which were
                            available before introducing
                            tMacFltrEntryActionTable and
                            tIPvXFltrEntryActionTable. All actions (including
                            action related functionality) can be configured via
                            tables tMacFltrEntryActionTable and
                            tIPvXFltrEntryActionTable. The value 'unrecognized'
                            indicates that the currently configured action was
                            added after introduction of tMacFltrEntryActionTable
                            and tIPvXFltrEntryActionTable and can't be
                            interpreted in the tables tMacFilterParamsTable,
                            tIPFilterParamsTable, tIPv6FilterParamsTable and
                            their augment tables.
                            "
    SYNTAX INTEGER {
        drop        (1),
        forward     (2),
        httpRedirect(4),
        nat         (5),
        reassemble  (6),
        gtpLclBrkout(7),
        forwardEsiL2(8),
        forwardEsiL3(9),
        unrecognized (11)
    }

TFilterPbrDownActionOvr ::= TEXTUAL-CONVENTION
    STATUS current
    DESCRIPTION
        "The textual convention TFilterPbrDownActionOvr specifies an override of
         default PBR down action:
         - none                  (0): default PBR down action is applied to
                                      packets matching the filter entry.
                                      Default PBR down action is either drop
                                      or forward based on PBR action type.
         - drop                  (1): packets matching the filter entry are
                                      dropped.
         - forward               (2): packets matching the filter entry are
                                      forwarded.
         - filterDefaultAction   (3): packets matching the filter entry are
                                      handled according to filter default action
                                      configured using tIPFilterDefaultAction
                                      for IP filter, tIPv6FilterDefaultAction
                                      for IPv6 filter and
                                      tMacFilterDefaultAction for MAC filter."
    SYNTAX INTEGER {
        none                  (0),
        drop                  (1),
        forward               (2),
        filterDefaultAction   (3)
    }

TFilterActionOrDefault ::= TEXTUAL-CONVENTION
    STATUS current
    DESCRIPTION
        "Action to take on a packet:
         - drop        (1): packets matching the filter entry are dropped.
         - forward     (2): packets matching the filter entry are forwarded.
         - default     (3): packets matching the filter entry get the applicable
                            default behavior. Note: the value 'default' is
                            currently not supported.
         - httpRedirect(4): packets matching the filter entry are redirected.
         - nat         (5): packets matching the filter entry are forwarded to
                            the NAT function in the system.
         - reassemble  (6): packets matching the filter entry are forwarded to
                            the packet REASSEMBLE function in the system.
         - gtpLclBrkout(7): packets matching the filter entry are broken out
                            locally from a GTP tunnel (and thereby bypass the
                            mobile packet core). For packets that are not sent
                            in the context of a GTP tunnel, this action is
                            equivalent to 'forward'.
         - forwardEsiL2(8): packets matching the filter entry are forwarded to
                            ESI identified first appliance in Nuage service
                            chain using EVPN-resolved VXLAN tunnel in
                            the specified VPLS service.
         - forwardEsiL3(9): packets matching the filter entry are forwarded to
                            ESI/SF-IP identified first appliance in Nuage
                            service chain using EVPN-resolved VXLAN tunnel over
                            the configured VAS interface in the specified VPRN
                            service.
         - unrecognized(11): Tables tMacFilterParamsTable, tIPFilterParamsTable,
                            tIPv6FilterParamsTable and their augment tables can
                            only be used to configure actions which were
                            available before introducing
                            tMacFltrEntryActionTable and
                            tIPvXFltrEntryActionTable. All actions (including
                            action related functionality) can be configured via
                            tables tMacFltrEntryActionTable and
                            tIPvXFltrEntryActionTable. The value 'unrecognized'
                            indicates that the currently configured action was
                            added after introduction of tMacFltrEntryActionTable
                            and tIPvXFltrEntryActionTable and can't be
                            interpreted in the tables tMacFilterParamsTable,
                            tIPFilterParamsTable, tIPv6FilterParamsTable and
                            their augment tables.
                            "
    SYNTAX INTEGER {
        drop        (1),
        forward     (2),
        default     (3),
        httpRedirect(4),
        nat         (5),
        reassemble  (6),
        gtpLclBrkout(7),
        forwardEsiL2(8),
        forwardEsiL3(9),
        unrecognized(11)
    }

TIPvXFilterEntryAction ::= TEXTUAL-CONVENTION
    STATUS current
    DESCRIPTION
        "Action to take on a packet:
         - drop                (1): A packet matching the entry will be dropped.
         - forward             (2): A packet matching the entry will be
                                    forwarded using regular routing.
         - httpRedirect        (4): An HTTP GET packet matching the entry is
                                    forwarded to CPM for HTTP captive portal
                                    processing.
         - nat                 (5): A packet matching the entry will be
                                    forwarded to NAT.
         - reassemble          (6): Packets matching the entry are forwarded to
                                    the packet REASSEMBLE function in the
                                    system.
         - gtpLclBrkout        (7): A packet matching the entry is broken out
                                    locally from a GTP tunnel (and thereby
                                    bypass the mobile packet core). For packets
                                    that are not sent in the context of a GTP
                                    tunnel, this action is equivalent to
                                    forward.
         - forwardEsiL2        (8): A packet matching the entry will be
                                    forwarded to ESI identified first appliance
                                    in Nuage service chain using EVPN-resolved
                                    VXLAN tunnel in the specified VPLS service.
         - forwardEsiL3        (9): A packet matching the entry will be
                                    forwarded to ESI/SF-IP identified first
                                    appliance in Nuage service chain using
                                    EVPN-resolved VXLAN tunnel over the
                                    configured VAS interface in the specified
                                    VPRN service.
         - ofPacketIn         (10): Packets are sent to controller configured
                                    for this H-OFS instance on a dedicated
                                    packet-in channel part of the main or
                                    auxiliary connection.
         - dropTtl            (12): A packet matching the entry will be dropped
                                    only if 'Time-to-live' field of packet's
                                    IPv4 header or 'Hop-Limit' field of packet's
                                    IPv6 header meets the configured condition.
         - dropPktLen         (13): A packet matching the entry will be dropped
                                    only if 'Total Length' field of packet's
                                    IPv4 header or 'Payload Length' field of
                                    packet's IPv6 header field meets the
                                    configured condition.
         - forwardRtr         (14): A packet matching the entry will be
                                    forwarded in the configured routing context.
         - forwardNextHop     (15): A packet matching the entry will be
                                    forwarded in the routing context of the
                                    incoming interface using direct or indirect
                                    IP address in the routing lookup.
         - forwardNextHopRtr  (16): A packet matching the entry will be
                                    forwarded in the configured routing context
                                    using direct or indirect IP address in the
                                    routing lookup.
         - forwardNHInterface (17): A packet matching the entry will be
                                    forwarded using the configured local
                                    interface.
         - forwardLsp         (18): A packet matching the entry will be
                                    forwarded using the specified LSP.
         - forwardSdp         (19): A packet matching the entry will be
                                    forwarded using the configured SDP.
         - forwardSap         (20): A packet matching the entry will be
                                    forwarded using the configured SAP.
         - forwardRPlcy       (21): A packet matching the entry will be
                                    forwarded using forward next-hop or forward
                                    next-hop router and the IP address of
                                    destination selected by the configured
                                    redirect policy.  If no destination is
                                    selected packets are subject to action
                                    forward.
         - rateLimit          (22): Traffic matching the entry will be limited
                                    to the value specified by the object
                                    tIPvXFltrEntryActRateLimit.
         - tcpMssAdjust       (23): The value of TCP Maximum Segment Size (MSS)
                                    option of packets matching the entry will be
                                    set to the value specified by
                                    TIMETRA-VRTR-MIB.mib::tmnxVrtrMssAdjSegmentSize
                                    if the value of the option exceeds that
                                    value or the option is not present at all.
         - remarkDscp         (24): DSCP value of packets matching the entry
                                    will be remarked.
                                   "
    SYNTAX INTEGER {
        drop              (1),
        forward           (2),
        httpRedirect      (4),
        nat               (5),
        reassemble        (6),
        gtpLclBrkout      (7),
        forwardEsiL2      (8),
        forwardEsiL3      (9),
        ofPacketIn        (10),
        dropTtl           (12),
        dropPktLen        (13),
        forwardRtr        (14),
        forwardNextHop    (15),
        forwardNextHopRtr (16),
        forwardNHInterface(17),
        forwardLsp        (18),
        forwardSdp        (19),
        forwardSap        (20),
        forwardRPlcy      (21),
        rateLimit         (22),
        tcpMssAdjust      (23),
        remarkDscp        (24)
    }

TFilterPbrTargetStatus ::= TEXTUAL-CONVENTION

    STATUS current
    DESCRIPTION
        "Status of PBR target :
         - unknown           (0): Status of PBR target is not tracked
         - doesNotExist      (1): The system does not know the PBR target.
         - up                (2): PBR target is known by the system and can be
                                  used for forwarding the traffic.
         - down              (3): PBR target is known by the system but can't be
                                  used for forwarding the traffic.
         "
    SYNTAX INTEGER {
        unknown (0),
        doesNotExist (1),
        up (2),
        down (3)
    }

TFilterDownloadedAction ::= TEXTUAL-CONVENTION

    STATUS current
    DESCRIPTION
        "Filter action downloaded to IOM:
         - none          (1): No filter entry action is downloaded to IOM.
                              Entry is inactive or filter is not applied.
         - primary       (2): Primary filter entry action is downloaded to IOM.
         - secondary     (3): Secondary filter entry action is downloaded to
                              IOM.
         - forward       (4): Neither primary nor secondary action is downloaded
                              to IOM. Action forward is downloaded to IOM.
         - drop          (5): Neither primary nor secondary action is downloaded
                              to IOM. Action drop is downloaded to IOM.
         - notDisplayed  (6): Field is not supported for configured action.
         "
    SYNTAX INTEGER {
        none (1),
        primary (2),
        secondary (3),
        forward (4),
        drop (5),
        notDisplayed (6)
    }

TFilterEntryActionId ::= TEXTUAL-CONVENTION
    STATUS current
    DESCRIPTION
        "The textual convention TFilterEntryActionId specifies the unique
         identifier and also the priority of the action within the filter
         entry."
    SYNTAX INTEGER {
        primary   (1),
        secondary (2)
    }

TMacFilterEntryAction ::= TEXTUAL-CONVENTION

    STATUS current
    DESCRIPTION
        "Action to take on a packet matching the filter entry:
         - drop              (1) : A packet matching the entry will be dropped.
         - forward           (2) : A packet matching the entry will be forwarded
                                   using regular routing.
         - httpRedirect      (4):  An HTTP GET packet matching the entry is
                                   forwarded to CPM for HTTP captive portal
                                   processing.
         - forwardEsiL2      (8):  A packet matching the entry will be forwarded
                                   to ESI identified first appliance in Nuage
                                   service chain using EVPN-resolved VXLAN
                                   tunnel in the specified VPLS service.
         - forwardSdp        (19): A packet matching the entry will be forwarded
                                   using the configured SDP.
         - forwardSap        (20): A packet matching the entry will be forwarded
                                   using the configured SAP.
         - rateLimit         (22): Traffic matching the entry will be limited to
                                   the value specified by the object
                                   tIPvXFltrEntryActRateLimit.
                                   "
    SYNTAX INTEGER {
        drop              (1),
        forward           (2),
        httpRedirect      (4),
        forwardEsiL2      (8),
        forwardSdp        (19),
        forwardSap        (20),
        rateLimit         (22)
    }

TIPvXFilterEntryActionExt ::= TEXTUAL-CONVENTION

    STATUS current
    DESCRIPTION
        "Action to take on a packet:
         - none              (0) : This value indicates that no action
                                   is specified.
         - remarkDscp        (24): DSCP value of packets will be remarked. 
                                   "
    SYNTAX INTEGER {
        none              (0),
        remarkDscp        (24)
    }

TFilterLogId ::= TEXTUAL-CONVENTION
    STATUS current
    DESCRIPTION
        "Uniquely identifies an entry in the filter log table. 0 indicates an
         invalid log-id."
    SYNTAX Unsigned32 (0 | 101..199)

TFilterLogDestination ::= TEXTUAL-CONVENTION
    STATUS current
    DESCRIPTION
        "Determines the location where filtered packets are logged."
    SYNTAX INTEGER {
        memory(1),
        syslog(2),
        file(3)
    }

TTimeRangeState ::= TEXTUAL-CONVENTION
    STATUS current
    DESCRIPTION
        "The textual convention TTimeRangeState is used to indicate the state
         of an object that is controlled by a time range.
         - timeRangeNotApplic:
           no time range is applicable for this entry.
         - timeRangeNotActive:
           A time range is defined but is not active at this moment.
         - timeRangeActive.
           A time range is defined, and is activated successfully.
         - timeRangeActiveDownloadFailed:
           A time range is defined and is activated, but the corresponding
           object could not be installed due to resource problems."
    SYNTAX INTEGER {
        timeRangeNotApplic(0),
        timeRangeNotActive(1),
        timeRangeActive(2),
        timeRangeActiveDownloadFailed(3)
    }

TFilterLogSummaryCriterium ::= TEXTUAL-CONVENTION
    STATUS current
    DESCRIPTION
        "Indicates the field on which log summarization will be done.
         - when set to srcAddr, received log packets are summarized
           based on the src ip/mac-addr
         - when set to dstAddr, received log packets are summarized
           based on the dst ip/mac-addr"
    SYNTAX INTEGER {
        srcAddr  (0),
        dstAddr  (1)
    }

TFilterType ::= TEXTUAL-CONVENTION
    STATUS current
    DESCRIPTION
        "Type of filter."
    SYNTAX INTEGER {
        fltrtypeselNone   (0),
        fltrtypeselIp     (1),
        fltrtypeselMac    (2),
        fltrtypeselCpm    (3),
        fltrtypeselIpv6   (4),
        fltrtypeselCpm6   (5),
        fltrtypeselCpmMac (6)
    }

TFilterSubInsSpaceOwner ::= TEXTUAL-CONVENTION
    STATUS current
    DESCRIPTION
        "Application capable of inserting filter entries into an
         existing filter"
    SYNTAX INTEGER {
        none             (0),
        radius           (1),
        creditControl    (2),
        bgpFlowspec      (3),
        li               (4),
        embedded         (5),
        radiusSharedHost (6),
        openflow         (7),
        pccRule          (8),
        vsd              (9)
    }

TDHCPFilterID ::= TEXTUAL-CONVENTION
    STATUS current
    DESCRIPTION
        "The identification number of a DHCP filter."
    SYNTAX TFilterID

TDhcpFilterAction ::= TEXTUAL-CONVENTION
    STATUS current
    DESCRIPTION
        "Action to take on DHCP host creation when the filter entry matches.

         When set to none(1), host creation proceeds as normal.

         When set to bypass-host-creation(2), host creation is bypassed.

         When set to drop(3), the DHCP message is dropped. "
    SYNTAX INTEGER {
        none                (1), 
        bypass-host-creation(2),
        drop                (3)
    }

TDhcpFilterMatch ::= TEXTUAL-CONVENTION
    STATUS current
    DESCRIPTION
        "Match condition for a DHCP option in a DHCP filter entry

         When set to present(1) the related DHCP option must be present,
         when set to absent(2) the related DHCP option must be absent.

         When set to string(3) the option must (partially) match a specified
         ASCII string, setting string-exact(4) requires an exact match, setting
         string-invert(5) requires the option not to (partially) match, setting
         string-exact-invert(6) requires the option not to match exact.

         Setting hex(7), hex-exact(8), hex-invert(9) or hex-exact-invert(10)
         will use a hex octet string for the matching."
    SYNTAX INTEGER {
        present            (1),
        absent             (2),
        string             (3),
        string-exact       (4),
        string-invert      (5),
        string-exact-invert(6),
        hex                (7),
        hex-exact          (8),
        hex-invert         (9),
        hex-exact-invert   (10)
    }

TFltrPrefixListType ::= TEXTUAL-CONVENTION
    STATUS current
    DESCRIPTION
        "The type TFltrPrefixListType enumerates all possible prefix list
         types."
    SYNTAX INTEGER {
        ipv4 (1),
        ipv6 (2)
    }

TmnxEmbeddedFltrOperState ::= TEXTUAL-CONVENTION
    STATUS current
    DESCRIPTION
        "The TmnxEmbeddedFltrOperState data type is an enumerated integer that
         describes the current operational state of a filter embedding request."
    SYNTAX INTEGER {
        embedFailedNoResources    (-1),
        inactive                  (0),
        active                    (1)
    }

TmnxEmbeddedFltrAdminState ::= TEXTUAL-CONVENTION
    STATUS      current
    DESCRIPTION
        "The TmnxEmbeddedFltrAdminState data type is an enumerated integer that
         describes the current administrative state of a filter embedding
         request."
    SYNTAX INTEGER {
        inactive  (0),
        active    (1)
    }

TmnxFltrEmbeddedEntryState ::= TEXTUAL-CONVENTION
    STATUS current
    DESCRIPTION
        "The TmnxFltrEmbeddedEntryState data type is an enumerated integer that
         describes the current operational state of an embedded filter entry."
    SYNTAX INTEGER {
        inserted(1),
        overruled(2),
        inactiveAdminDown(3),
        inactiveNoResources(4)
    }

TmnxFilterApplyPathSource ::= TEXTUAL-CONVENTION
    STATUS current
    DESCRIPTION
        "The TmnxFilterApplyPathSource data type is an enumerated integer that
         describes the source of the apply-path imported prefixes"
    SYNTAX INTEGER {
        unknown   (0),
        bgp-peers (1)
    }

TFltrPortSelector ::= TEXTUAL-CONVENTION
    STATUS current
    DESCRIPTION
        "This textual convention specifies how the source-port and
         destination-port filter objects are combined to form the filter match
         criterion.
         - If the selector takes the value and-port(0) then the source-port
           and destination-port objects (if set) are combined into 1 filter
           condition that fires if both conditions are met (i.e. a logical
           and-operation of both is done). If one of them is not set (default
           values) then only the other one is taken into account for the match
           condition.
         - If the selector takes the value or-port(1) then the source-port
           objects are used as match condition for either source-port or
           destination-port (i.e. a logical or-operation is done). In this case,
           non-default values must be set for the source-port objects. In this
           case the destination-port objects are (silently) copied from the
           source-port objects by the system; any other values set by the user
           are overwritten by the system."
    SYNTAX INTEGER {
        and-port(0),
        or-port(1)
    }

TFilterPacketLength ::= TEXTUAL-CONVENTION
    STATUS current
    DESCRIPTION
        "The TFilterPacketLength textual convention is used to specify the
         'Total Length' value of packet's IPv4 header or the 'Payload Length'
         value of packet's IPv6 header."
    SYNTAX Unsigned32 (0..65535)

TFilterTTL ::= TEXTUAL-CONVENTION
    STATUS current
    DESCRIPTION
        "The TFilterTTL textual convention is used to specify
         a Time To Live (IPv4) or Hop Limit (IPv6) value."
    SYNTAX Unsigned32 (0..255)

TmnxFilterRPlcyTestLastAction ::= TEXTUAL-CONVENTION
    STATUS current
    DESCRIPTION
        "The TmnxFilterRPlcyTestLastAction textual convention is used
         to indicate the last impact of a test assigned to a destination of
         a redirect policy on an operational state of the destination.

         Value 'enable' indicates the operational state of the destination
         has been set to 'inService'.

         Value 'disable' indicates the operational state of the destination
         has been set to 'outOfService'.

         Value 'none' indicates the operational state of the destination
         has not been changed yet."
    SYNTAX INTEGER {
        enable (1),
        disable (2),
        none (3)
    }

TmnxFilterRPlcyTestRespAction ::= TEXTUAL-CONVENTION
    STATUS current
    DESCRIPTION
        "The TmnxFilterRPlcyTestRespAction textual convention is used
         to indicate the action of a test assigned to a destination of
         a redirect policy on a operational priority of the destination.

         Value 'increase' indicates that if the response passes the test
         the operational priority of the destination will be increased.

         Value 'decrease' indicates that if the response passes the test
         the operational priority of the destination will be decreased.

         Value 'disable' indicates the test wont have impact on the
         operational priority of the destination."
    SYNTAX INTEGER {
        increase (1),
        decrease (2),
        disable (3)
    }

TFilterEgressPBR ::= TEXTUAL-CONVENTION
    STATUS current
    DESCRIPTION
        "disable         - 0: policy based routing has no effect when applied
                              on egress
         enable          - 1: egress policy based routing is allowed and default
                              load-balancing based on hash of source/destination
                              address of the packet is applied
         enableWithL4LB  - 2: egress policy based routing is allowed and
                              l4-load-balancing is applied (if available include
                              TCP/UDP port in hash."
    SYNTAX INTEGER {
        disable        (0),
        enable         (1),
        enableWithL4LB (2)
    }

TFilterEsi ::= TEXTUAL-CONVENTION
    STATUS current
    DESCRIPTION
        "Ethernet Segment Identifier (ESI) as defined in IETF draft
         BGP MPLS Based Ethernet VPN. ESI is a unique non-zero identifier that
         identifies an Ethernet Segment. ESI is encoded as a ten octets integer
         in line format with the most significant octet sent first.
         The following two ESI values are reserved:
             - ESI 0 denotes a single-homed CE.
             - ESI {0xFF} (repeated 10 times) is known as MAX-ESI.

         In a network with managed and not-managed CEs, the ESI has the
         following format:

                      +---+---+---+---+---+---+---+---+---+---+
                      | T |          ESI Value                |
                      +---+---+---+---+---+---+---+---+---+---+

          Where:
          T (ESI Type) is a 1-octet field (most significant octet) that
          specifies the format of the remaining nine octets (ESI Value).
          ESI type can be one of the values 0x00-0x05."
    SYNTAX OCTET STRING ( SIZE(10) )

TFilterEntryActionRateLimit ::= TEXTUAL-CONVENTION
    STATUS current
    DESCRIPTION
        "A limiting rate in kilobits-per-second for traffic matching
         the filter entry. The value -1 means max rate."
    SYNTAX Integer32 (-1 | 0..2000000000)

TFilterEmbedOffset ::= TEXTUAL-CONVENTION
    STATUS current
    DESCRIPTION
        "Insertion offset of entries of an embedded filter into an embedding
         filter. An entry at position x in the embedded filter is inserted
         at position x + offset in the embedding filter."
    SYNTAX Unsigned32 (0..65536)

--
-- mib objects
--

--
-- IP Filter Table
--

tIPFilterTable OBJECT-TYPE
    SYNTAX      SEQUENCE OF TIPFilterEntry
    MAX-ACCESS  not-accessible
    STATUS      current
    DESCRIPTION
        "Contains a List of all ip filters configured on this system."
    ::= { tFilterObjects 1 }

tIPFilterEntry OBJECT-TYPE
    SYNTAX      TIPFilterEntry
    MAX-ACCESS  not-accessible
    STATUS      current
    DESCRIPTION
        "Information about a particular IP Filter entry. Entries are
         created/deleted  by user. Entries have a presumed StorageType of
         nonVolatile."
    INDEX { tIPFilterId }
    ::= { tIPFilterTable 1 }

TIPFilterEntry ::= SEQUENCE
    {
        tIPFilterId                      TAnyFilterID,
        tIPFilterRowStatus               RowStatus,
        tIPFilterScope                   TFilterScope,
        tIPFilterDescription             TItemDescription,
        tIPFilterDefaultAction           TFilterAction,
        tIPFilterRadiusInsertPt          TEntryIdOrZero,
        tIPFilterRadiusInsertSize        TEntryIdOrZero,
        tIPFilterCreditCntrlInsertPt     TEntryIdOrZero,
        tIPFilterCreditCntrlInsertSize   TEntryIdOrZero,
        tIPFilterSubInsertHighWmark      Integer32,
        tIPFilterSubInsertLowWmark       Integer32,
        tIpFilterCreditCntrlNbrInsertd   Unsigned32,
        tIpFilterRadiusNbrInsertd        Unsigned32,
        tIpFilterName                    TLNamedItemOrEmpty,
        tIPFilterHostSharedInsertPt      TEntryIdOrZero,
        tIPFilterHostSharedInsertSize    TEntryIdOrZero,
        tIpFilterHostSharedNbrInsertd    Unsigned32,
        tIPFilterHostSharedHighWmark     Integer32,
        tIPFilterHostSharedLowWmark      Integer32,
        tIPFilterNbrHostSharedFltrs      Unsigned32,
        tIPFilterSharedPccRuleInsrtPt    TEntryIdOrZero,
        tIPFilterSharedPccRuleInsrtSize  TEntryIdOrZero,
        tIPFilterSharedPccRuleNbrInsrtd  Unsigned32,        
        tIPFilterChainToSystemFilter     TruthValue
    }

tIPFilterId OBJECT-TYPE
    SYNTAX      TAnyFilterID
    MAX-ACCESS  not-accessible
    STATUS      current
    DESCRIPTION
        "The value of the object tIPFilterId uniquely identifies an ip filter.
         User-configured filters have values between (1..65535).
         Other values are reserved for filters that are created (auto-generated)
         by the system.
         Refer to the description of the textual convention TAnyFilterID
         for more details."
    ::= { tIPFilterEntry 1 }

tIPFilterRowStatus OBJECT-TYPE
    SYNTAX      RowStatus
    MAX-ACCESS  read-create
    STATUS      current
    DESCRIPTION
        "This object allows entries to be created and deleted in the
         tIPFilterTable."
    ::= { tIPFilterEntry 2 }

tIPFilterScope OBJECT-TYPE
    SYNTAX      TFilterScope
    MAX-ACCESS  read-create
    STATUS      current
    DESCRIPTION
        "This object specifies the scope of this filter definition."
    DEFVAL { template }
    ::= { tIPFilterEntry 3 }

tIPFilterDescription OBJECT-TYPE
    SYNTAX      TItemDescription
    MAX-ACCESS  read-create
    STATUS      current
    DESCRIPTION
        "User-provided description for this filter."
    DEFVAL { ''H }
    ::= { tIPFilterEntry 4 }

tIPFilterDefaultAction OBJECT-TYPE
    SYNTAX      TFilterAction
    MAX-ACCESS  read-create
    STATUS      current
    DESCRIPTION
        "The action to take for packets that do not match any filter entries.
         The only allowed values for this field are drop(1) and forward(2)."
    DEFVAL { drop }
    ::= { tIPFilterEntry 5 }

tIPFilterRadiusInsertPt OBJECT-TYPE
    SYNTAX      TEntryIdOrZero
    MAX-ACCESS  read-create
    STATUS      current
    DESCRIPTION
        "The value of tIPFilterRadiusInsertPt specifies at what place the
         host specific filter entries received from Radius will be inserted
         in the filter.

         The area defined here will be dedicated to those entries, no other
         entries will be allowed.

         The value 0 means that no Radius provided host specific filter
         entries can be inserted in the filter.

         If tIPFilterRadiusInsertSize is set to 0, then this object
         will be put to 0 as well. Any change attempts will be
         silently discarded in this case."
    DEFVAL { 0 }
    ::= { tIPFilterEntry 6 }

tIPFilterRadiusInsertSize OBJECT-TYPE
    SYNTAX      TEntryIdOrZero
    MAX-ACCESS  read-create
    STATUS      current
    DESCRIPTION
        "The value of tIPFilterRadiusInsertSize specifies how many
         host specific filter entries received from Radius for subscriber
         hosts can be inserted in the filter.

         If tIPFilterRadiusInsertPt is set to 0, then this object
         will be put to 0 as well. Any change attempts will be
         silently discarded in this case."
    DEFVAL { 0 }
    ::= { tIPFilterEntry 7 }

tIPFilterCreditCntrlInsertPt OBJECT-TYPE
    SYNTAX      TEntryIdOrZero
    MAX-ACCESS  read-create
    STATUS      current
    DESCRIPTION
        "The value of tIPFilterCreditCntrlInsertPt specifies at what place
         the filter entries received from Credit Control for a
         particular subscriber host will be inserted in the filter.

         The area defined here will be dedicated to those entries, no other
         entries will be allowed.

         The value 0 means that no Credit Control provided filter entries
         can be inserted in the filter.

         If tIPFilterCreditCntrlInsertSize is set to 0, then this object
         will be put to 0 as well. Any change attempts will be
         silently discarded in this case."
    DEFVAL { 0 }
    ::= { tIPFilterEntry 8 }

tIPFilterCreditCntrlInsertSize OBJECT-TYPE
    SYNTAX      TEntryIdOrZero
    MAX-ACCESS  read-create
    STATUS      current
    DESCRIPTION
        "The value of tIPFilterCreditCntrlInsertSize specifies how many
         filter entries received from Credit Control can be inserted in the
         filter.

         If tIPFilterCreditCntrlInsertPt is set to 0, then this object
         will be put to 0 as well. Any change attempts will be
         silently discarded in this case."
    DEFVAL { 0 }
    ::= { tIPFilterEntry 9 }

tIPFilterSubInsertHighWmark OBJECT-TYPE
    SYNTAX      Integer32 (0..100)
    MAX-ACCESS  read-create
    STATUS      current
    DESCRIPTION
        "The value of the object tIPFilterSubInsertHighWmark
         specifies the utilization of the filter ranges for filter
         entry insertion, at which a table full alarm will be raised
         by the agent."
    DEFVAL { 95 }
    ::= { tIPFilterEntry 10 }

tIPFilterSubInsertLowWmark OBJECT-TYPE
    SYNTAX      Integer32 (0..100)
    MAX-ACCESS  read-create
    STATUS      current
    DESCRIPTION
        "The value of the object tIPFilterSubInsertLowWmark
         specifies the utilization of the filter ranges for filter
         entry insertion, at which a table full alarm will be cleared
         by the agent."
    DEFVAL { 90 }
    ::= { tIPFilterEntry 11 }

tIpFilterCreditCntrlNbrInsertd OBJECT-TYPE
    SYNTAX      Unsigned32
    MAX-ACCESS  read-only
    STATUS      current
    DESCRIPTION
        "The value of the object tIpFilterCreditCntrlNbrInsertd
         indicates how many filter entries are currently inserted
         in the filter on request of credit control."
    ::= { tIPFilterEntry 12 }

tIpFilterRadiusNbrInsertd OBJECT-TYPE
    SYNTAX      Unsigned32
    MAX-ACCESS  read-only
    STATUS      current
    DESCRIPTION
        "The value of the object tIpFilterRadiusNbrInsertd
         indicates how many host specific filter entries are
         currently inserted in the filter on request of RADIUS."
    ::= { tIPFilterEntry 13 }

tIpFilterName OBJECT-TYPE
    SYNTAX      TLNamedItemOrEmpty
    MAX-ACCESS  read-create
    STATUS      current
    DESCRIPTION
        "The value of tIpFilterName specifies the name to associate
        with this filter."
    DEFVAL { ''H }
    ::= { tIPFilterEntry 14 }

tIPFilterHostSharedInsertPt OBJECT-TYPE
    SYNTAX      TEntryIdOrZero
    MAX-ACCESS  read-create
    STATUS      current
    DESCRIPTION
        "The value of tIPFilterHostSharedInsertPt specifies at what place the
         filter entries received from Radius that are shared between several
         hosts (host common rules) will be inserted in the filter.
    
         The area defined here will be dedicated to those entries, no other
         entries will be allowed.
    
         The value 0 means that no Radius provided host common filter entries
         can be inserted in the filter.
    
         If tIPFilterHostSharedInsertSize is set to 0, then this object
         will be put to 0 as well. Any change attempts will be
         silently discarded in this case."
    DEFVAL { 0 }
    ::= { tIPFilterEntry 15 }

tIPFilterHostSharedInsertSize OBJECT-TYPE
    SYNTAX      TEntryIdOrZero
    MAX-ACCESS  read-create
    STATUS      current
    DESCRIPTION
        "The value of tIPFilterHostSharedInsertSize specifies how many
         host common filter entries received from Radius for subscriber hosts
         can be inserted in the filter.
    
         If tIPFilterHostSharedInsertPt is set to 0, then this object
         will be put to 0 as well. Any change attempts will be
         silently discarded in this case."
    DEFVAL { 0 }
    ::= { tIPFilterEntry 16 }

tIpFilterHostSharedNbrInsertd OBJECT-TYPE
    SYNTAX      Unsigned32
    MAX-ACCESS  read-only
    STATUS      current
    DESCRIPTION
        "The value of the object tIpFilterHostSharedNbrInsertd
         indicates how many Radius Shared Filter rules are
         inserted in the filter."
    ::= { tIPFilterEntry 17 }

tIPFilterHostSharedHighWmark OBJECT-TYPE
    SYNTAX      Integer32 (-1 | 1..8000)
    MAX-ACCESS  read-create
    STATUS      current
    DESCRIPTION
        "The value of the object tIPFilterHostSharedHighWmark
         specifies the number of Radius Shared Filters that can be 
         dynamically created in the system before an high watermark
         notification is generated by the system.
         The value -1 specifies that no notifications are sent.
         If any of the watermarks (high or low) is set to -1, both
         watermarks will be set to -1 by the system."
    DEFVAL { -1 }
    ::= { tIPFilterEntry 18 }

tIPFilterHostSharedLowWmark OBJECT-TYPE
    SYNTAX      Integer32  (-1 | 0..8000)
    MAX-ACCESS  read-create
    STATUS      current
    DESCRIPTION
        "The value of the object tIPFilterHostSharedLowWmark
         specifies the number of Radius Shared Filters that are still
         dynamically created in the system before an high watermark
         notification is cleared by the system.
         The value -1 specifies that no notifications are sent.
         If any of the watermarks (high or low) is set to -1, both
         watermarks will be set to -1 by the system."
    DEFVAL { -1 }
    ::= { tIPFilterEntry 19 }

tIPFilterNbrHostSharedFltrs OBJECT-TYPE
    SYNTAX      Unsigned32
    MAX-ACCESS  read-only
    STATUS      current
    DESCRIPTION
        "The value of the object tIPFilterNbrHostSharedFltrs indicates how many
         filters are currently created by Radius or Diameter based on this
         filter. (Both host shared or flow-rule filters.)"
    ::= { tIPFilterEntry 20 }

tIPFilterSharedPccRuleInsrtPt OBJECT-TYPE
    SYNTAX      TEntryIdOrZero
    MAX-ACCESS  read-create
    STATUS      current
    DESCRIPTION
        "The value of tIPFilterSharedPccRuleInsrtPt specifies at what place the
         flow-rule filter entries that are received from Diameter and that are
         shared across several hosts will be inserted in the filter.

         The range defined here will be reserved for those entries; no other
         entries will be allowed in this range.

         The value 0 means that no flow-rule filter entries can be inserted in
         the filter by Diameter.

         If tIPFilterSharedPccRuleInsrtSize is set to 0 then
         tIPFilterSharedPccRuleInsrtPt is also set to 0 by the system.

         Note that the range reserved for shared flow-rule entries must not
         overlap with that of either
         tIPFilterRadiusInsertPt/tIPFilterRadiusInsertSize,
         tIPFilterCreditCntrlInsertPt/tIPFilterCreditCntrlInsertSize, or
         tIPFilterHostSharedInsertPt/tIPFilterHostSharedInsertSize"
    DEFVAL { 0 }
    ::= { tIPFilterEntry 21 }

tIPFilterSharedPccRuleInsrtSize OBJECT-TYPE
    SYNTAX      TEntryIdOrZero
    MAX-ACCESS  read-create
    STATUS      current
    DESCRIPTION
        "The value of tIPFilterSharedPccRuleInsrtSize specifies how many
         flow-rule filter entries that are received from Diameter and that are
         shared across several hosts can be inserted in the filter.

         The range defined here will be reserved for those entries; no other
         entries will be allowed in this range.

         The value 0 means that no flow-rule filter entries can be inserted in
         the filter by Diameter.

         If tIPFilterSharedPccRuleInsrtPt is set to 0 then
         tIPFilterSharedPccRuleInsrtSize is also set to 0 by the system.

         Note that the range reserved for shared flow-rule entries must not
         overlap with that of either
         tIPFilterRadiusInsertPt/tIPFilterRadiusInsertSize,
         tIPFilterCreditCntrlInsertPt/tIPFilterCreditCntrlInsertSize, or
         tIPFilterHostSharedInsertPt/tIPFilterHostSharedInsertSize"
    DEFVAL { 0 }
    ::= { tIPFilterEntry 22 }

tIPFilterSharedPccRuleNbrInsrtd OBJECT-TYPE
    SYNTAX      Unsigned32
    MAX-ACCESS  read-only
    STATUS      current
    DESCRIPTION
        "The value of the object tIPFilterSharedPccRuleNbrInsrtd indicates how
         many flow-rule filter entries received from Diameter have been inserted
         in this filter"
    ::= { tIPFilterEntry 23 }

tIPFilterChainToSystemFilter OBJECT-TYPE
    SYNTAX      TruthValue
    MAX-ACCESS  read-create
    STATUS      current
    DESCRIPTION
        "The value of the object tIPFilterChainToSystemFilter specifies
         whether this filter policy is chained to the active IP system filter
         policy.

         The active IP system filter policy is defined as a row in
         tFilterSystemFilterTable that have the value of the object
         tFilterSystemFilterType set to 'fltrtypeselIp(1)'.

         The value 'true(1)' means this filter policy is chained to
         the active IP system filter policy. The system filter policy's rules
         are executed first before any rules of this filter policy are
         executed.

         The value of this object can be set to 'true(1)' only when the scope
         of this policy (value of the object tIPFilterScope) is 'exclusive(1)'
         or 'template(2)'.

         The value 'false(2)' means this filter policy is not chained to
         the active IP system filter policy."
    DEFVAL { false }
    ::= { tIPFilterEntry 24 }

--
-- IP Filter Entry parameters
--

tIPFilterParamsTable OBJECT-TYPE
    SYNTAX      SEQUENCE OF TIPFilterParamsEntry
    MAX-ACCESS  not-accessible
    STATUS      current
    DESCRIPTION  "A table of all IP filter match entries for all IP filters."
    ::= { tFilterObjects 2 }

tIPFilterParamsEntry OBJECT-TYPE
    SYNTAX      TIPFilterParamsEntry
    MAX-ACCESS  not-accessible
    STATUS      current
    DESCRIPTION
        "Information about a particular IP Filter entry.
        Every IP Filter can have zero or more IP Filter match entries.

        A filter entry with no match criteria set will match every
        packet, and the entry action will be taken.

        Entries are created/deleted by user.

        Additional parameters can be found in tIPFilterParamsExtTable.

        There is no StorageType object, entries have a presumed
        StorageType of nonVolatile.
        "
    INDEX { tIPFilterId, tIPFilterParamsIndex }
    ::= { tIPFilterParamsTable 1 }

TIPFilterParamsEntry ::= SEQUENCE
    {
        tIPFilterParamsIndex               TAnyEntryId,
        tIPFilterParamsRowStatus           RowStatus,
        tIPFilterParamsLogId               TFilterLogId,
        tIPFilterParamsDescription         TItemDescription,
        tIPFilterParamsAction              TFilterActionOrDefault,
        tIPFilterParamsForwardNH           IpAddress,
        tIPFilterParamsForwardNHIndirect   TruthValue,
        tIPFilterParamsRemarkDSCP          TDSCPFilterActionValue,
        tIPFilterParamsRemarkDSCPMask      TDSCPFilterActionValue,
        tIPFilterParamsRemarkDot1p         Dot1PPriority,
        tIPFilterParamsSourceIpAddr        IpAddress,
        tIPFilterParamsSourceIpMask        IpAddressPrefixLength,
        tIPFilterParamsDestinationIpAddr   IpAddress,
        tIPFilterParamsDestinationIpMask   IpAddressPrefixLength,
        tIPFilterParamsProtocol            TIpProtocol,
        tIPFilterParamsSourcePortValue1    TTcpUdpPort,
        tIPFilterParamsSourcePortValue2    TTcpUdpPort,
        tIPFilterParamsSourcePortOperator  TOperator,
        tIPFilterParamsDestPortValue1      TTcpUdpPort,
        tIPFilterParamsDestPortValue2      TTcpUdpPort,
        tIPFilterParamsDestPortOperator    TOperator,
        tIPFilterParamsDSCP                TDSCPNameOrEmpty,
        tIPFilterParamsFragment            TItemMatch,
        tIPFilterParamsOptionPresent       TItemMatch,
        tIPFilterParamsIpOptionValue       TIpOption,
        tIPFilterParamsIpOptionMask        TIpOption,
        tIPFilterParamsMultipleOption      TItemMatch,
        tIPFilterParamsTcpSyn              TItemMatch,
        tIPFilterParamsTcpAck              TItemMatch,
        tIPFilterParamsIcmpCode            INTEGER,
        tIPFilterParamsIcmpType            INTEGER,
        tIPFilterParamsCflowdSample        TruthValue,
        tIPFilterParamsCflowdIfSample      TruthValue,
        tIPFilterParamsForwardNHInterface  DisplayString,
        tIPFilterParamsIngressHitCount     Counter64,
        tIPFilterParamsEgressHitCount      Counter64,
        tIPFilterParamsLogInstantiated     TruthValue,
        tIPFilterParamsForwardRedPlcy      TNamedItemOrEmpty,
        tIPFilterParamsActiveDest          IpAddress,
        tIPFilterParamsFwdSvcId            TmnxServId,
        tIPFilterParamsFwdSapPortId        TmnxPortID,
        tIPFilterParamsFwdSapEncapVal      TmnxEncapVal,
        tIPFilterParamsFwdSdpBind          SdpBindId,
        tIPFilterParamsTimeRangeName       TNamedItemOrEmpty,
        tIPFilterParamsTimeRangeState      TTimeRangeState,
        tIPFilterParamsRedirectURL         TmnxHttpRedirectUrl,
        tIPFilterParamsSrcIpFullMask       IpAddress,
        tIPFilterParamsDestIpFullMask      IpAddress,
        tIPFilterParamsIngrHitByteCount    Counter64,
        tIPFilterParamsEgrHitByteCount     Counter64,
        tIPFilterParamsFwdRtrId            TmnxVRtrIDOrZero,
        tIPFilterParamsSrcRouteOption      TItemMatch,
        tIPFilterParamsSrcIpPrefixList     TNamedItemOrEmpty,
        tIPFilterParamsDstIpPrefixList     TNamedItemOrEmpty,
        tIPFilterParamsPortSelector        TFltrPortSelector,
        tIPFilterParamsSrcPortList         TNamedItemOrEmpty,
        tIPFilterParamsDstPortList         TNamedItemOrEmpty,
        tIPFilterParamsRdirAllwRadOvrd     TruthValue,
        tIPFilterParamsNatPolicyName       TNamedItemOrEmpty,
        tIPFilterParamsFwdLsp              TmnxVRtrMplsLspID,
        tIPFilterParamsFwdLspRtrId         TmnxVRtrIDOrZero
    }

tIPFilterParamsIndex OBJECT-TYPE
    SYNTAX      TAnyEntryId
    MAX-ACCESS  not-accessible
    STATUS      current
    DESCRIPTION
        "This is the secondary index for the entry. Every ip filter can have
         multiple entries, therefore every ip filter entry is identified by
         the tIPFilterId and tIPFilterParamsIndex.
         
         Refer to the description of the textual convention TAnyEntryId for more
         info on the allowed values for this object."
    ::= { tIPFilterParamsEntry 1 }

tIPFilterParamsRowStatus OBJECT-TYPE
    SYNTAX      RowStatus
    MAX-ACCESS  read-create
    STATUS      current
    DESCRIPTION
        "This object allows entries to be created and deleted in the
         tIPFilterParamsTable."
    ::= { tIPFilterParamsEntry 2 }

tIPFilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tIPFilterParamsEntry 3 }

tIPFilterParamsDescription OBJECT-TYPE
    SYNTAX      TItemDescription
    MAX-ACCESS  read-create
    STATUS      current
    DESCRIPTION
        "User-provided description for this filter entry."
    DEFVAL { ''H }
    ::= { tIPFilterParamsEntry 4 }

tIPFilterParamsAction OBJECT-TYPE
    SYNTAX      TFilterActionOrDefault
    MAX-ACCESS  read-create
    STATUS      current
    DESCRIPTION
        "The action to take for packets that match this filter entry. The value
         default(3) specifies this entry to inherit the behavior defined as the
         default for the filter.

         Setting the values 'forwardEsiL2' and 'forwardEsiL3' explicitly is
         ignored by the system. The values 'forwardEsiL2'(8) and
         'forwardEsiL3'(9) can be set only implicitly by specifying non default
         values of objects specifying parameters for these actions. In such case
         the value of tIPFilterParamsAction will be set to 'forwardEsiL2'(8) or
         'forwardEsiL3'(9) automatically by system.

         The object tIPFilterParamsAction supports only subset of filter
         actions. The object tIPvXFltrEntryActAction supports all actions. It's
         recommended to use tIPvXFltrEntryActAction instead of
         tIPFilterParamsAction.
         "
    DEFVAL { drop }
    ::= { tIPFilterParamsEntry 5 }

tIPFilterParamsForwardNH OBJECT-TYPE
    SYNTAX      IpAddress
    MAX-ACCESS  read-create
    STATUS      current
    DESCRIPTION
        "The ip-address of the nexthop to which the packet should be forwarded
         if it hits this filter entry. The action of this entry should be
         'forward' in such a case.

         Note that the value of tIPFilterParamsForwardNH is silently cleared
         by the system if tIPFilterParamsAction is set to value other than
         'forward'(2), or any object related to 'forward' other than
         tIPFilterParamsForwardNH, tIPFilterParamsForwardNHIndirect
         or tIPFilterParamsFwdRtrId is set."
    DEFVAL { '00000000'H }
    ::= { tIPFilterParamsEntry 6 }

tIPFilterParamsForwardNHIndirect OBJECT-TYPE
    SYNTAX      TruthValue
    MAX-ACCESS  read-create
    STATUS      current
    DESCRIPTION
        "tIPFilterParamsForwardNHIndirect specifies if the nexthop is directly/
         indirectly reachable.

         Note that the value of tIPFilterParamsForwardNHIndirect is silently
         cleared by the system if tIPFilterParamsAction is set to value other
         than 'forward'(2), or any object related to 'forward' other than
         tIPFilterParamsForwardNH, tIPFilterParamsForwardNHIndirect
         or tIPFilterParamsFwdRtrId is set."
    DEFVAL { false }
    ::= { tIPFilterParamsEntry 7 }

tIPFilterParamsRemarkDSCP OBJECT-TYPE
    SYNTAX      TDSCPFilterActionValue
    MAX-ACCESS  read-create
    STATUS      obsolete
    DESCRIPTION
        "The DSCP value that should be remarked in case a packet hits this
         filter entry."
    DEFVAL { -1 }
    ::= { tIPFilterParamsEntry 8 }

tIPFilterParamsRemarkDSCPMask OBJECT-TYPE
    SYNTAX      TDSCPFilterActionValue
    MAX-ACCESS  read-create
    STATUS      obsolete
    DESCRIPTION
        "tIPFilterParamsRemarkDSCPMask specifies the care bits while remarking
         with the DSCP value."
    DEFVAL { 255 }
    ::= { tIPFilterParamsEntry 9 }

tIPFilterParamsRemarkDot1p OBJECT-TYPE
    SYNTAX      Dot1PPriority
    MAX-ACCESS  read-create
    STATUS      obsolete
    DESCRIPTION
        "tIPFilterParamsRemarkDot1p specifies the Dot1p value that needs to be
         remarked on the packet if it hits this filter entry."
    DEFVAL { -1 }
    ::= { tIPFilterParamsEntry 10 }

tIPFilterParamsSourceIpAddr OBJECT-TYPE
    SYNTAX      IpAddress
    MAX-ACCESS  read-create
    STATUS      current
    DESCRIPTION
        "IP address to match the source-ip of the packet."
    DEFVAL { '00000000'H }
    ::= { tIPFilterParamsEntry 11 }

tIPFilterParamsSourceIpMask OBJECT-TYPE
    SYNTAX      IpAddressPrefixLength
    MAX-ACCESS  read-create
    STATUS      current
    DESCRIPTION
        "If different from 0, the object tIPFilterParamsSourceIpMask
         specifies the IP Mask value for this policy IP Filter entry.
         The mask is ANDed with the received source IP address to match
         the tIPFilterParamsSourceIpAddr.

         If the value of tIPFilterParamsSourceIpMask is 0, and the
         value of tIPFilterParamsSrcIpFullMask is non zero then the
         value of tIPFilterParamsSrcIpFullMask is used as mask.

         If the value of tIPFilterParamsSourceIpMask is non zero,
         it will be equal to the mask expressed the object
         tIPFilterParamsSrcIpFullMask.

         If both tIPFilterParamsSourceIpMask and
         tIPFilterParamsSrcIpFullMask are set to 0, no matching is done
         on the source Ip address.

         If a value is specified for this object, then the value of the
         object tIPFilterParamsSrcIpFullMask will be set to reflect
         this same mask."
    DEFVAL { 0 }
    ::= { tIPFilterParamsEntry 12 }

tIPFilterParamsDestinationIpAddr OBJECT-TYPE
    SYNTAX      IpAddress
    MAX-ACCESS  read-create
    STATUS      current
    DESCRIPTION
        "IP address to match the destination-ip of the packet."
    DEFVAL { '00000000'H }
    ::= { tIPFilterParamsEntry 13 }

tIPFilterParamsDestinationIpMask OBJECT-TYPE
    SYNTAX      IpAddressPrefixLength
    MAX-ACCESS  read-create
    STATUS      current
    DESCRIPTION
        "If different from 0, the object tIPFilterParamsDestinationIpMask
         specifies the IP Mask value for this policy IP Filter entry.
         The mask is ANDed with the received Destination IP address to match
         the tIPFilterParamsDestinationIpAddr.

         If the value of tIPFilterParamsDestinationIpMask is 0, and the
         value of tIPFilterParamsDestIpFullMask is non zero then the
         value of tIPFilterParamsDestIpFullMask is used as mask.

         If the value of tIPFilterParamsDestinationIpMask is non zero,
         it will be equal to the mask expressed the object
         tIPFilterParamsDestIpFullMask.

         If both tIPFilterParamsDestinationIpMask and
         tIPFilterParamsDestIpFullMask are set to 0, no matching is done
         on the Destination Ip address.

         If a value is specified for this object, then the value of the
         object tIPFilterParamsDestIpFullMask will be set to reflect
         this same mask."
    DEFVAL { 0 }
    ::= { tIPFilterParamsEntry 14 }

tIPFilterParamsProtocol OBJECT-TYPE
    SYNTAX      TIpProtocol
    MAX-ACCESS  read-create
    STATUS      current
    DESCRIPTION
        "IP protocol to match. Set to -1 to disable matching IP protocol. If
         the protocol is changed the protocol specific parameters are reset.
         For instance if protocol is changed from TCP to UDP, then the objects
         tIPFilterParamsTcpSyn and tIPFilterParamsTcpAck will be turned off."
    DEFVAL { -1 }
    ::= { tIPFilterParamsEntry 15 }

tIPFilterParamsSourcePortValue1 OBJECT-TYPE
    SYNTAX      TTcpUdpPort
    MAX-ACCESS  read-create
    STATUS      current
    DESCRIPTION
        "TCP/UDP port value1. The value of this object is used as per the
         description for tIPFilterParamsSourcePortOperator."
    DEFVAL { 0 }
    ::= { tIPFilterParamsEntry 16 }

tIPFilterParamsSourcePortValue2 OBJECT-TYPE
    SYNTAX      TTcpUdpPort
    MAX-ACCESS  read-create
    STATUS      current
    DESCRIPTION
        "TCP/UDP port value2. The value of this object is used as per the
         description for tIPFilterParamsSourcePortOperator."
    DEFVAL { 0 }
    ::= { tIPFilterParamsEntry 17 }

tIPFilterParamsSourcePortOperator OBJECT-TYPE
    SYNTAX      TOperator
    MAX-ACCESS  read-create
    STATUS      current
    DESCRIPTION
        "The operator specifies the manner in which
         tIPFilterParamsSourcePortValue1 and tIPFilterParamsSourcePortValue2
         are to be used. The value of these latter 2 objects and
         tIPFilterParamsSourcePortOperator is used as described in
         TTcpUdpPortOperator."
    DEFVAL { none }
    ::= { tIPFilterParamsEntry 18 }

tIPFilterParamsDestPortValue1 OBJECT-TYPE
    SYNTAX      TTcpUdpPort
    MAX-ACCESS  read-create
    STATUS      current
    DESCRIPTION
        "TCP/UDP port value1. The value of this object is used as per the
         description for tIPFilterParamsDestPortOperator."
    DEFVAL { 0 }
    ::= { tIPFilterParamsEntry 19 }

tIPFilterParamsDestPortValue2 OBJECT-TYPE
    SYNTAX      TTcpUdpPort
    MAX-ACCESS  read-create
    STATUS      current
    DESCRIPTION
        "TCP/UDP port value2. 
        
         The value of this object is used as per the
         description for tIPFilterParamsDestPortOperator."
    DEFVAL { 0 }
    ::= { tIPFilterParamsEntry 20 }

tIPFilterParamsDestPortOperator OBJECT-TYPE
    SYNTAX      TOperator
    MAX-ACCESS  read-create
    STATUS      current
    DESCRIPTION
        "The operator specifies the manner in which
         tIPFilterParamsDestPortValue1 and tIPFilterParamsDestPortValue2
         are to be used. The value of these latter 2 objects and
         tIPFilterParamsDestPortOperator is used as described in
         TTcpUdpPortOperator."
    DEFVAL { none }
    ::= { tIPFilterParamsEntry 21 }

tIPFilterParamsDSCP OBJECT-TYPE
    SYNTAX      TDSCPNameOrEmpty
    MAX-ACCESS  read-create
    STATUS      current
    DESCRIPTION
        "DSCP to be matched on the packet."
    DEFVAL { ''H }
    ::= { tIPFilterParamsEntry 22 }

tIPFilterParamsFragment OBJECT-TYPE
    SYNTAX      TItemMatch
    MAX-ACCESS  read-create
    STATUS      current
    DESCRIPTION
        "If enabled, this object matches fragmented/unfragmented packets as per
         the value of the object."
    DEFVAL { off }
    ::= { tIPFilterParamsEntry 24 }

tIPFilterParamsOptionPresent OBJECT-TYPE
    SYNTAX      TItemMatch
    MAX-ACCESS  read-create
    STATUS      current
    DESCRIPTION
        "If enabled, this object matches packets if they have options present
         or not as per the value of the object."
    DEFVAL { off }
    ::= { tIPFilterParamsEntry 25 }

tIPFilterParamsIpOptionValue OBJECT-TYPE
    SYNTAX      TIpOption
    MAX-ACCESS  read-create
    STATUS      current
    DESCRIPTION
        "The value of the specific ip-option to match."
    DEFVAL { 0 }
    ::= { tIPFilterParamsEntry 26 }

tIPFilterParamsIpOptionMask OBJECT-TYPE
    SYNTAX      TIpOption
    MAX-ACCESS  read-create
    STATUS      current
    DESCRIPTION
        "Mask is ANDed with the ip-option before being compared to
        tIPFilterParamsIpOptionValue."
    DEFVAL { 0 }
    ::= { tIPFilterParamsEntry 27 }

tIPFilterParamsMultipleOption OBJECT-TYPE
    SYNTAX      TItemMatch
    MAX-ACCESS  read-create
    STATUS      current
    DESCRIPTION
        "If enabled, matches multiple options as per the value of the object."
    DEFVAL { off }
    ::= { tIPFilterParamsEntry 28 }

tIPFilterParamsTcpSyn OBJECT-TYPE
    SYNTAX      TItemMatch
    MAX-ACCESS  read-create
    STATUS      current
    DESCRIPTION
        "If Enabled, matches a TCP Syn as per value of the object."
    DEFVAL { off }
    ::= { tIPFilterParamsEntry 29 }

tIPFilterParamsTcpAck OBJECT-TYPE
    SYNTAX      TItemMatch
    MAX-ACCESS  read-create
    STATUS      current
    DESCRIPTION
        "If Enabled, matches a TCP Ack as per value of the object."
    DEFVAL { off }
    ::= { tIPFilterParamsEntry 30 }

tIPFilterParamsIcmpCode OBJECT-TYPE
    SYNTAX      INTEGER (-1|0..255)
    MAX-ACCESS  read-create
    STATUS      current
    DESCRIPTION
        "Icmp code to be matched. tIPFilterParamsIcmpCode complements the
        object tIPFilterParamsIcmpType. Both of them need to be set to actually
        enable ICMP matching. The value -1 means Icmp code matching is not
        enabled."
    DEFVAL { -1 }
    ::= { tIPFilterParamsEntry 31 }

tIPFilterParamsIcmpType OBJECT-TYPE
    SYNTAX      INTEGER (-1|0..255)
    MAX-ACCESS  read-create
    STATUS      current
    DESCRIPTION
        "Icmp type to be matched. tIPFilterParamsIcmpType complements the
        object tIPFilterParamsIcmpCode. Both of them need to be set to actually
        enable ICMP matching. The value -1 means Icmp type matching is not
        enabled."
    DEFVAL { -1 }
    ::= { tIPFilterParamsEntry 32 }

tIPFilterParamsCflowdSample OBJECT-TYPE
    SYNTAX      TruthValue
    MAX-ACCESS  read-create
    STATUS      current
    DESCRIPTION
        "When tIPFilterParamsCflowdSample has a value of 'true',  Cflowd
         sampling and analysis is performed on those packet streams where this
         filter has been applied.  Only packets matching this IP filter entry
         are subjected to Cflowd sampling and analysis.  A Cflowd profile
         controls the sampling and analysis of data flows through the router."
    DEFVAL { false }
    ::= { tIPFilterParamsEntry 33 }

tIPFilterParamsCflowdIfSample OBJECT-TYPE
    SYNTAX      TruthValue
    MAX-ACCESS  read-create
    STATUS      current
    DESCRIPTION
        "When tIPFilterParamsCflowdIfSample has a value of 'true', Cflowd
         sampling and analysis is performed on those packet streams where this
         filter has been applied.  Only packets matching this IP filter entry
         are subjected to Cflowd sampling and analysis.  A Cflowd profile
         controls the sampling and analysis of data flows through the router."
    DEFVAL { true }
    ::= { tIPFilterParamsEntry 34 }

tIPFilterParamsForwardNHInterface OBJECT-TYPE
    SYNTAX      DisplayString (SIZE(0..32))
    MAX-ACCESS  read-create
    STATUS      current
    DESCRIPTION
        "The interface name for the nexthop to which the packet should be
         forwarded if it hits this filter entry. The action of this entry
         should be 'forward' in such a case.

         Note that the value of tIPFilterParamsForwardNHInterface is silently
         cleared  by the system if tIPFilterParamsAction is set to value other
         than 'forward'(2) or any object related to 'forward' other than
         this one is set."
    DEFVAL { ''H }
    ::= { tIPFilterParamsEntry 35 }

tIPFilterParamsIngressHitCount OBJECT-TYPE
    SYNTAX      Counter64
    MAX-ACCESS  read-only
    STATUS      current
    DESCRIPTION
        "This object indicates the number of times an ingress packet
         matched this entry."
    ::= { tIPFilterParamsEntry 36 }

tIPFilterParamsEgressHitCount OBJECT-TYPE
    SYNTAX      Counter64
    MAX-ACCESS  read-only
    STATUS      current
    DESCRIPTION
        "This object indicates the number of times an egress packet
         matched this entry."
    ::= { tIPFilterParamsEntry 37 }

tIPFilterParamsLogInstantiated OBJECT-TYPE
    SYNTAX      TruthValue
    MAX-ACCESS  read-only
    STATUS      current
    DESCRIPTION
        "tIPFilterParamsLogInstantiated indicates if the filter log for
         this filter entry has been instantiated or not."
    ::= { tIPFilterParamsEntry 38 }

tIPFilterParamsForwardRedPlcy OBJECT-TYPE
    SYNTAX      TNamedItemOrEmpty
    MAX-ACCESS  read-create
    STATUS      current
    DESCRIPTION
        "tIPFilterParamsForwardRedPlcy specifies the redirect policy to be
         used to determine the nexthop.

         Note that the value of tIPFilterParamsForwardRedPlcy is silently
         cleared  by the system if tIPFilterParamsAction is set to value other
         than 'forward'(2) or any object related to 'forward' other than
         this one is set."
    DEFVAL { ''H }
    ::= { tIPFilterParamsEntry 39 }

tIPFilterParamsActiveDest OBJECT-TYPE
    SYNTAX      IpAddress
    MAX-ACCESS  read-only
    STATUS      current
    DESCRIPTION
        "tIPFilterParamsActiveDest indicates the IP address of the active
         destination for this IP filter. A value of 0 indicates that there
         is currently no active destination."
    ::= { tIPFilterParamsEntry 40 }

tIPFilterParamsFwdSvcId OBJECT-TYPE
    SYNTAX      TmnxServId
    MAX-ACCESS  read-only
    STATUS      current
    DESCRIPTION
        "tIPFilterParamsFwdSvcId indicates the service id of the
         destination for this IP filter entry. A value of 0 indicates that
         there is currently no active SAP or SDP destination."
    ::= { tIPFilterParamsEntry 41 }

tIPFilterParamsFwdSapPortId OBJECT-TYPE
    SYNTAX      TmnxPortID
    MAX-ACCESS  read-create
    STATUS      current
    DESCRIPTION
        "tIPFilterParamsFwdSapPortId specifies the sap port identity of the
         destination for this IP filter entry.

         A value of 0 indicates that there is currently no SAP destination
         defined. A value different from 0 can only be specified if the value
         of the tIPFilterParamsAction object of this entry is 'forward'.
         In addition a non-zero value can only be given if the object
         tIPFilterParamsFwdSdpBind has a zero value.

         Note that the value of tIPFilterParamsFwdSapPortId is silently cleared
         by the system if tIPFilterParamsAction is set to value other than
         'forward'(2) or any object related to 'forward' other than
         tIPFilterParamsFwdSapPortId, tIPFilterParamsFwdSapEncapVal is set."
    DEFVAL { 0 }
    ::= { tIPFilterParamsEntry 42 }

tIPFilterParamsFwdSapEncapVal OBJECT-TYPE
    SYNTAX      TmnxEncapVal
    MAX-ACCESS  read-create
    STATUS      current
    DESCRIPTION
        "tIPFilterParamsFwdSapEncapVal specifies the sap port encap value
         of the destination SAP for this IP filter entry.

         A value different from 0 can only be specified if the value of the
         tIPFilterParamsAction object of this entry is 'forward'.  In addition
         a non-zero value can only be given if the object
         tIPFilterParamsFwdSdpBind has a zero value. A value of 0 indicates
         that either
         1) the sap encapsulation value is not specified when
            tIPFilterParamsFwdSapPortId and tIPFilterParamsFwdSvcId
            have valid values; or
         2) that there is no SAP destination.

         Note that the value of tIPFilterParamsFwdSapEncapVal is silently
         cleared  by the system if tIPFilterParamsAction is set to value other
         than 'forward'(2) or any object related to 'forward' other than
         tIPFilterParamsFwdSapPortId or tIPFilterParamsFwdSapEncapVal is set."
    DEFVAL { 0 }
    ::= { tIPFilterParamsEntry 43 }

tIPFilterParamsFwdSdpBind OBJECT-TYPE
    SYNTAX      SdpBindId
    MAX-ACCESS  read-create
    STATUS      current
    DESCRIPTION
        "tIPFilterParamsFwdSdpBind specifies the sdp bind identity of the
         destination for this IP filter entry.

         A value of 0 indicates that there is currently no SDP binding defined.
         A value different from 0 can only be specified if the value of the
         tIPFilterParamsAction object of this entry is 'forward'. In addition
         a non-zero value can only be given if the objects
         tIPFilterParamsFwdSapPortId and tIPFilterParamsFwdSapEncapVal have a
         zero value.

         Note that the value of tIPFilterParamsFwdSdpBind is silently cleared
         by the system if tIPFilterParamsAction is set to value other
         than 'forward'(2) or any object related to 'forward' other than
         this one is set."
    DEFVAL { '0000000000000000'H }
    ::= { tIPFilterParamsEntry 44 }

tIPFilterParamsTimeRangeName OBJECT-TYPE
    SYNTAX      TNamedItemOrEmpty
    MAX-ACCESS  read-create
    STATUS      obsolete
    DESCRIPTION
        "tIPFilterParamsTimeRangeName specifies the tmnxTimeRangeEntry to be
         associated with this filter entry.

         A value for this object can only be specified during row creation, and
         cannot be altered later on.
         Also, a value is accepted only if the tmnxTimeRangeEntry is defined
         in the TIMETRA-SCHEDULER-MIB::tmnxTimeRangeTable.tTimeRangeName.

         This object is obsoleted in release 14.0."
    DEFVAL { ''H }
    ::= { tIPFilterParamsEntry 45 }

tIPFilterParamsTimeRangeState OBJECT-TYPE
    SYNTAX      TTimeRangeState
    MAX-ACCESS  read-only
    STATUS      obsolete
    DESCRIPTION
        "tIPFilterParamsTimeRangeState indicates whether or not the entry
         is currently in effect.
         - timeRangeNotApplic:
           no time range is applicable for this entry.
         - timeRangeNotActive:
           A time range is defined in tIPFilterParamsTimeRangeName, but is not
           active at this moment. Consequently the filter entry is not
           installed.
         - timeRangeActive.
           A time range is defined in tIPFilterParamsTimeRangeName, and is
           activated successfully.
         - timeRangeActiveDownloadFailed:
           A time range is defined in tIPFilterParamsTimeRangeName, and is
           activated, but the corresponding filter entry could not be
           installed due to resource problems.

         This object is obsoleted in release 14.0."
    ::= { tIPFilterParamsEntry 46 }

tIPFilterParamsRedirectURL OBJECT-TYPE
    SYNTAX      TmnxHttpRedirectUrl
    MAX-ACCESS  read-create
    STATUS      current
    DESCRIPTION
        "The value of tIPFilterParamsRedirectURL specifies the URL
         to redirect to, when the value of tIPFilterParamsAction is
         'httpRedirect'.

         The following macro substitutions are applicable in this context:
         $URL, $MAC, $IP, $SUB, $SAP, $SAPDESC, $CID, and $RID.

         Note that the value of tIPFilterParamsRedirectURL is silently cleared
         by the system if tIPFilterParamsAction is set to any value other than
         httpRedirect."
    DEFVAL { ''H }
    ::= { tIPFilterParamsEntry 47 }

tIPFilterParamsSrcIpFullMask OBJECT-TYPE
    SYNTAX      IpAddress
    MAX-ACCESS  read-create
    STATUS      current
    DESCRIPTION
        "If different from 0, the object tIPFilterParamsSrcIpFullMask
         specifies the IP Mask value for this policy IP Filter entry.
         The mask is ANDed with the received Source IP address to match
         the tIPFilterParamsSourceIpAddr.

         If the value of tIPFilterParamsSourceIpMask is non zero,
         it will be equal to the mask expressed the object
         tIPFilterParamsSrcIpFullMask.

         If both tIPFilterParamsSourceIpMask and
         tIPFilterParamsSrcIpFullMask are set to 0, no matching is done
         on the Source Ip address.

         This object should contain consecutive ones and zeros. Both
         a regular and an inverse mask is allowed (i.e. the sequence of
         consecutive ones can appear at the front or at the end of the
         mask).

         If a regular mask is specified for tIPFilterParamsSrcIpFullMask
         then the value of tIPFilterParamsSourceIpMask will be changed
         to reflect this value. If an inverse is specified, the value of
         tIPFilterParamsSourceIpMask will be set to 0."
    DEFVAL { '0000'H }
    ::= { tIPFilterParamsEntry 48 }

tIPFilterParamsDestIpFullMask OBJECT-TYPE
    SYNTAX      IpAddress
    MAX-ACCESS  read-create
    STATUS      current
    DESCRIPTION
        "If different from 0, the object tIPFilterParamsDestIpFullMask
         specifies the IP Mask value for this policy IP Filter entry.
         The mask is ANDed with the received Destination IP address to match
         the tIPFilterParamsDestinationIpAddr.

         If the value of tIPFilterParamsDestinationIpMask is non zero,
         it will be equal to the mask expressed the object
         tIPFilterParamsDestIpFullMask.

         If both tIPFilterParamsDestinationIpMask and
         tIPFilterParamsDestIpFullMask are set to 0, no matching is done
         on the Destination Ip address.

         This object should contain consecutive ones and zeros. Both
         a regular and an inverse mask is allowed (i.e. the sequence of
         consecutive ones can appear at the front or at the end of the
         mask).

         If a regular mask is specified for tIPFilterParamsDestIpFullMask
         then the value of tIPFilterParamsDestinationIpMask will be changed
         to reflect this value. If an inverse is specified, the value of
         tIPFilterParamsDestinationIpMask will be set to 0."
    DEFVAL { '0000'H }
    ::= { tIPFilterParamsEntry 49 }

tIPFilterParamsIngrHitByteCount OBJECT-TYPE
    SYNTAX      Counter64
    MAX-ACCESS  read-only
    STATUS      current
    DESCRIPTION
        "The value of tIPFilterParamsIngrHitByteCount indicates the number
         of bytes of all ingress packets that matched this entry."
    ::= { tIPFilterParamsEntry 50 }

tIPFilterParamsEgrHitByteCount OBJECT-TYPE
    SYNTAX      Counter64
    MAX-ACCESS  read-only
    STATUS      current
    DESCRIPTION
        "The value of tIPFilterParamsEgrHitByteCount indicates the number
         of bytes of all egress packets that matched this entry."
    ::= { tIPFilterParamsEntry 51 }

tIPFilterParamsFwdRtrId OBJECT-TYPE
    SYNTAX      TmnxVRtrIDOrZero
    MAX-ACCESS  read-create
    STATUS      current
    DESCRIPTION
        "tIPFilterParamsFwdRtrId specifies, if different from '0',
         the router id into which the packet should be forwarded
         if it hits this filter entry.

         The action of this entry should be 'forward' in such a case.

         Note that the value of tIPFilterParamsFwdRtrId is silently cleared
         by the system if tIPFilterParamsAction is set to value other
         than 'forward'(2) or any object related to 'forward' other than
         tIPFilterParamsFwdRtrId, tIPFilterParamsForwardNH or
         tIPFilterParamsForwardNHIndirect is set."
    DEFVAL { 0 }
    ::= { tIPFilterParamsEntry 52 }

tIPFilterParamsSrcRouteOption OBJECT-TYPE
    SYNTAX      TItemMatch
    MAX-ACCESS  read-create
    STATUS      current
    DESCRIPTION
        "tIPFilterParamsSrcRouteOption specifies, when enabled,
         that this filter should match if a (strict or loose) source route
         option is present/not present at any location within the IP header,
         as per the value of this object."
    DEFVAL { off }
    ::= { tIPFilterParamsEntry 53 }

tIPFilterParamsSrcIpPrefixList OBJECT-TYPE
    SYNTAX      TNamedItemOrEmpty
    MAX-ACCESS  read-create
    STATUS      current
    DESCRIPTION
        "The value of this object specifies the ip-prefix-list used as match
         criterion for the source ip address.

         The value specified for this object must correspond to a prefix-list
         defined in tFilterPrefixListTable.

         If the value of this object is empty then the values of the objects
         tIPFilterParamsSourceIpAddr and tIPFilterParamsSourceIpMask are used as
         source ip address match criterion.

         When this object is set to a non-empty value then the objects
         tIPFilterParamsSourceIpAddr and tIPFilterParamsSourceIpMask are reset
         to their default values by the system.

         Vice versa, when a new (non-default) value is provided for the objects
         tIPFilterParamsSourceIpAddr and tIPFilterParamsSourceIpMask then this
         object is reset to its default (empty) value by the system.

         An attempt to set tIPFilterParamsSrcIpPrefixList to a non-default value
         in combination with setting any of tIPFilterParamsSourceIpAddr or
         tIPFilterParamsSourceIpMask to (a) non-default value(s) is rejected by
         the system"
    DEFVAL { ''H }
    ::= { tIPFilterParamsEntry 54 }

tIPFilterParamsDstIpPrefixList OBJECT-TYPE
    SYNTAX      TNamedItemOrEmpty
    MAX-ACCESS  read-create
    STATUS      current
    DESCRIPTION
        "The value of this object specifies the ip-prefix-list used as match
         criterion for the destination ip address.

         The value specified for this object must correspond to a prefix-list
         defined in tFilterPrefixListTable.

         If the value of this object is empty then the values of the objects
         tIPFilterParamsDestinationIpAddr and tIPFilterParamsDestinationIpMask
         are used as destination ip address match criterion.

         When this object is set to a non-empty value then the objects
         tIPFilterParamsDestinationIpAddr and tIPFilterParamsDestinationIpMask
         are reset to their default values by the system.

         Vice versa, when a new (non-default) value is provided for the objects
         tIPFilterParamsDestinationIpAddr and tIPFilterParamsDestinationIpMask
         then this object is reset to its default (empty) value by the system.

         An attempt to set tIPFilterParamsDstIpPrefixList to a non-default value
         in combination with setting any of tIPFilterParamsDestinationIpAddr or
         tIPFilterParamsDestinationIpMask to (a) non-default value(s) is
         rejected by the system"
    DEFVAL { ''H }
    ::= { tIPFilterParamsEntry 55 }

tIPFilterParamsPortSelector OBJECT-TYPE
    SYNTAX      TFltrPortSelector
    MAX-ACCESS  read-create
    STATUS      current
    DESCRIPTION
        "This object specifies how the source-port objects
         (tIPFilterParamsSourcePortValue1, tIPFilterParamsSourcePortValue2,
         tIPFilterParamsSourcePortOperator, tIPFilterParamsSrcPortList) and
         destination-port objects (tIPFilterParamsDestPortValue1,
         tIPFilterParamsDestPortValue2, tIPFilterParamsDestPortOperator,
         tIPFilterParamsDstPortList) are combined to form the filter match
         criterion. See description of TFltrPortSelector."
    DEFVAL { and-port }
    ::= { tIPFilterParamsEntry 56 }

tIPFilterParamsSrcPortList OBJECT-TYPE
    SYNTAX      TNamedItemOrEmpty
    MAX-ACCESS  read-create
    STATUS      current
    DESCRIPTION
        "The value of this object specifies the port-list used as match
         criterion for the source port.

         The value specified for this object must correspond to a port-list
         defined in tFilterPortListTable.

         If the value of this object is empty then the values of the objects
         tIPFilterParamsSourcePortValue1, tIPFilterParamsSourcePortValue2, and
         tIPFilterParamsSourcePortOperator are used as source port match
         criterion.

         When this object is set to a non-empty value then the objects
         tIPFilterParamsSourcePortValue1, tIPFilterParamsSourcePortValue2, and
         tIPFilterParamsSourcePortOperator are reset to their default values by
         the system.

         Vice versa, when a new (non-default) value is provided for one of the
         objects tIPFilterParamsSourcePortValue1,
         tIPFilterParamsSourcePortValue2, or tIPFilterParamsSourcePortOperator
         then tIPFilterParamsSrcPortList is reset to its default (empty) value
         by the system.

         Setting any one of the objects tIPFilterParamsSourcePortValue1,
         tIPFilterParamsSourcePortValue2, or tIPFilterParamsSourcePortOperator
         to a non-default value in combination with a non-default value for the
         object tIPFilterParamsSrcPortList is rejected by the system."
    DEFVAL { ''H }
    ::= { tIPFilterParamsEntry 57 }

tIPFilterParamsDstPortList OBJECT-TYPE
    SYNTAX      TNamedItemOrEmpty
    MAX-ACCESS  read-create
    STATUS      current
    DESCRIPTION
        "The value of this object specifies the port-list used as match
         criterion for the destination port.

         The value specified for this object must correspond to a port-list
         defined in tFilterPortListTable.

         If the value of this object is empty then the values of the objects
         tIPFilterParamsDestPortValue1, tIPFilterParamsDestPortValue2, and
         tIPFilterParamsDestPortOperator are used as destination port match
         criterion.

         When this object is set to a non-empty value then the objects
         tIPFilterParamsDestPortValue1, tIPFilterParamsDestPortValue2, and
         tIPFilterParamsDestPortOperator are reset to their default values by
         the system.

         Vice versa, when a new (non-default) value is provided for one of the
         objects tIPFilterParamsDestPortValue1, tIPFilterParamsDestPortValue2,
         or tIPFilterParamsDestPortOperator then tIPFilterParamsDstPortList is
         reset to its default (empty) value by the system.

         Setting any one of the objects tIPFilterParamsDestPortValue1,
         tIPFilterParamsDestPortValue2, or tIPFilterParamsDestPortOperator
         to a non-default value in combination with a non-default value for the
         object tIPFilterParamsDstPortList is rejected by the system."
    DEFVAL { ''H }
    ::= { tIPFilterParamsEntry 58 }

tIPFilterParamsRdirAllwRadOvrd OBJECT-TYPE
    SYNTAX      TruthValue
    MAX-ACCESS  read-create
    STATUS      current
    DESCRIPTION
        "The value of this object specifies whether or not the value of
         tIPFilterParamsRedirectURL can be over-ridden by a Radius VSA. The
         default value is false (i.e. the URL cannot be over-ridden by Radius).
         The value of tIPFilterParamsRdirAllwRadOvrd is relevant only if the
         value of tIPFilterParamsAction is httpRedirect.

         Setting the value of tIPFilterParamsRdirAllwRadOvrd to true is
         ignored by the system if the value of tIPFilterParamsAction is not
         httpRedirect. Furthermore, the value of
         tIPFilterParamsRdirAllwRadOvrd is silently reset to false by the
         system if tIPFilterParamsAction is set to any value other than
         httpRedirect."
    DEFVAL { false }
    ::= { tIPFilterParamsEntry 59 }

tIPFilterParamsNatPolicyName OBJECT-TYPE
    SYNTAX      TNamedItemOrEmpty
    MAX-ACCESS  read-create
    STATUS      current
    DESCRIPTION
        "The value of this object specifies the name of the NAT policy to be
         used when the value of tIPFilterParamsAction is nat. If the value is
         empty then a default policy is used. If the value is non-empty then it
         must correspond to a policy defined in tmnxNatPlcyTable.

         The value of tIPFilterParamsNatPolicyName is relevant only if the value
         of tIPFilterParamsAction is nat. Setting the value of
         tIPFilterParamsNatPolicyName to a non-empty string is ignored by the
         system if the value of tIPFilterParamsAction is not nat.

         Furthermore, the value of tIPFilterParamsNatPolicyName is silently
         reset to an empty string by the system if tIPFilterParamsAction is set
         to any value other than nat."
    DEFVAL { "" }
    ::= { tIPFilterParamsEntry 60 }

tIPFilterParamsFwdLsp OBJECT-TYPE
    SYNTAX      TmnxVRtrMplsLspID (0..65535)
    MAX-ACCESS  read-create
    STATUS      current
    DESCRIPTION
         "If different from zero the value of the object tIPFilterParamsFwdLsp
          together with the value of the object tIPFilterParamsFwdLspRtrId
          specifies the LSP into which a packet should be forwarded if it hits
          this filter entry.

          The value of the object tIPFilterParamsAction of this entry
          must be 'forward' in such case. Otherwise the value of the object
          tIPFilterParamsFwdLsp is ignored by the system.

          Note that the value of tIPFilterParamsFwdLsp is reset to '0'
          by the system if tIPFilterParamsAction is set to value other
          than 'forward'(2) or any object related to 'forward' other than
          tIPFilterParamsFwdLsp or tIPFilterParamsFwdLspRtrId is set.

          The value of the object tIPFilterParamsFwdLsp cannot be set to a
          non-zero value if other destinations are already specified.

          The value has to be '0' if the value of the object
          tIPFilterParamsFwdLspRtrId is not set (i.e. is '0').

          If a non-zero value is set, the value of the object
          tIPFilterParamsFwdLspRtrId has to be set as well."
    DEFVAL { 0 }
    ::= { tIPFilterParamsEntry 61 }

tIPFilterParamsFwdLspRtrId OBJECT-TYPE
    SYNTAX      TmnxVRtrIDOrZero
    MAX-ACCESS  read-create
    STATUS      current
    DESCRIPTION
         "The value of the object tIPFilterParamsFwdLspRtrId specifies
          the router ID that the LSP ID defined by the value of the object
          tIPFilterParamsFwdLsp belongs to.

          The value of the object tIPFilterParamsAction of this entry
          must be 'forward' in such case. Otherwise the value of the object
          tIPFilterParamsFwdLspRtrId is ignored by the system.

          Note that the value of tIPFilterParamsFwdLspRtrId is reset to '0'
          by the system if tIPFilterParamsAction is set to value other
          than 'forward'(2) or any object related to 'forward' other than
          tIPFilterParamsFwdLsp or tIPFilterParamsFwdLspRtrId is set.

          The value of this object cannot be set to a non-zero value if
          other destinations are already specified.

          The value has to be '0' if the value of the object
          tIPFilterParamsFwdLsp is not set (i.e. is '0').

          If a non-zero value is set, the value of the object
          tIPFilterParamsFwdLsp has to be set as well.

          The ID of the base router or '0' are the only allowed value with this
          version of the product."
    DEFVAL { 0 }
    ::= { tIPFilterParamsEntry 62 }

--
-- MAC filter table
--

tMacFilterTable OBJECT-TYPE
    SYNTAX      SEQUENCE OF TMacFilterEntry
    MAX-ACCESS  not-accessible
    STATUS      current
    DESCRIPTION
        "Contains a List of all mac filters configured on this system."
    ::= { tFilterObjects 3 }

tMacFilterEntry OBJECT-TYPE
    SYNTAX      TMacFilterEntry
    MAX-ACCESS  not-accessible
    STATUS      current
    DESCRIPTION
        "Information about a particular MAC Filter. Entries are created/deleted
         by user. Entries have a presumed StorageType of nonVolatile."
    INDEX { tMacFilterId }
    ::= { tMacFilterTable 1 }

TMacFilterEntry ::= SEQUENCE
    {
        tMacFilterId            TConfigOrVsdFilterID,
        tMacFilterRowStatus     RowStatus,
        tMacFilterScope         TFilterScope,
        tMacFilterDescription   TItemDescription,
        tMacFilterDefaultAction TFilterAction,
        tMacFilterType          TMacFilterType,
        tMacFilterName          TLNamedItemOrEmpty
    }

tMacFilterId OBJECT-TYPE
    SYNTAX      TConfigOrVsdFilterID
    MAX-ACCESS  not-accessible
    STATUS      current
    DESCRIPTION
        "Uniquely identifies a mac filter as configures on this system.

         Values outside of range 1..65535 are reserved for entries dynamically
         created by the system and cannot be used in any SNMP SET operation.
         "
    ::= { tMacFilterEntry 1 }

tMacFilterRowStatus OBJECT-TYPE
    SYNTAX      RowStatus
    MAX-ACCESS  read-create
    STATUS      current
    DESCRIPTION
        "This object allows entries to be created and deleted in the
         tMacFilterTable."
    ::= { tMacFilterEntry 2 }

tMacFilterScope OBJECT-TYPE
    SYNTAX      TFilterScope
    MAX-ACCESS  read-create
    STATUS      current
    DESCRIPTION
        "This object specifies the scope of this filter definition.

         The value 'system(4)' is not supported."
    DEFVAL { template }
    ::= { tMacFilterEntry 3 }

tMacFilterDescription OBJECT-TYPE
    SYNTAX      TItemDescription
    MAX-ACCESS  read-create
    STATUS      current
    DESCRIPTION
        "User-provided description for this filter."
    DEFVAL { ''H }
    ::= { tMacFilterEntry 4 }

tMacFilterDefaultAction OBJECT-TYPE
    SYNTAX      TFilterAction
    MAX-ACCESS  read-create
    STATUS      current
    DESCRIPTION
        "The action to take for packets that do not match any filter entries.
         The only allowed values for this field are drop(1) and forward(2)."
    DEFVAL { drop }
    ::= { tMacFilterEntry 5 }

tMacFilterType OBJECT-TYPE
    SYNTAX      TMacFilterType
    MAX-ACCESS  read-create
    STATUS      current
    DESCRIPTION
        "tMacFilterType specifies which type of entries this mac filter
         can contain.

         If tMacFilterType is set to 'normal(1)', all match criteria
         are accepted except the criteria mentioned below that belong to type
         isid(2) and vid(3).

         If tMacFilterType is set to 'isid(2)' the only accepted match
         criteria for the filter entries are:
         - tMacFilterParamsLowISID
         - tMacFilterParamsHighISID

         If tMacFilterType is set to vid(3) the only accepted match
         criteria for the filter entries are:
         - tMacFilterParamsInnerTagValue
         - tMacFilterParamsInnerTagMask
         - tMacFilterParamsOuterTagValue
         - tMacFilterParamsOuterTagMask

         tMacFilterType can only be changed if the filter is not applied
         and has no entries."
    DEFVAL { normal }
    ::= { tMacFilterEntry 6 }

tMacFilterName OBJECT-TYPE
    SYNTAX      TLNamedItemOrEmpty
    MAX-ACCESS  read-create
    STATUS      current
    DESCRIPTION
        "The value of tMacFilterName specifies the name to associate
        with this filter."
    DEFVAL { ''H }
    ::= { tMacFilterEntry 7 }

--
-- MAC Filter Entry parameters
--

tMacFilterParamsTable OBJECT-TYPE
    SYNTAX      SEQUENCE OF TMacFilterParamsEntry
    MAX-ACCESS  not-accessible
    STATUS      current
    DESCRIPTION  "A table of all MAC filter match entries for all MAC filters."
    ::= { tFilterObjects 4 }

tMacFilterParamsEntry OBJECT-TYPE
    SYNTAX      TMacFilterParamsEntry
    MAX-ACCESS  not-accessible
    STATUS      current
    DESCRIPTION
        "Information about a particular MAC Filter entry.
         Every MAC Filter can have zero or more MAC Filter match entries.

         A filter entry with no match criteria set will match every
         packet, and the entry action will be taken.

         Entries are created/deleted by user.

         There is no StorageType object, entries have a presumed
         StorageType of nonVolatile."
    INDEX { tMacFilterId, tMacFilterParamsIndex }
    ::= { tMacFilterParamsTable 1 }

TMacFilterParamsEntry ::= SEQUENCE
    {
        tMacFilterParamsIndex            TEntryId,
        tMacFilterParamsRowStatus        RowStatus,
        tMacFilterParamsLogId            TFilterLogId,
        tMacFilterParamsDescription      TItemDescription,
        tMacFilterParamsAction           TFilterActionOrDefault,
        tMacFilterParamsFrameType        TFrameType,
        tMacFilterParamsSrcMAC           MacAddress,
        tMacFilterParamsSrcMACMask       MacAddress,
        tMacFilterParamsDstMAC           MacAddress,
        tMacFilterParamsDstMACMask       MacAddress,
        tMacFilterParamsDot1pValue       Dot1PPriority,
        tMacFilterParamsDot1pMask        Dot1PPriority,
        tMacFilterParamsEtherType        INTEGER,
        tMacFilterParamsDsap             ServiceAccessPoint,
        tMacFilterParamsDsapMask         ServiceAccessPoint,
        tMacFilterParamsSsap             ServiceAccessPoint,
        tMacFilterParamsSsapMask         ServiceAccessPoint,
        tMacFilterParamsSnapPid          INTEGER,
        tMacFilterParamsSnapOui          INTEGER,
        tMacFilterParamsIngressHitCount  Counter64,
        tMacFilterParamsEgressHitCount   Counter64,
        tMacFilterParamsLogInstantiated  TruthValue,
        tMacFilterParamsFwdSvcId         TmnxServId,
        tMacFilterParamsFwdSapPortId     TmnxPortID,
        tMacFilterParamsFwdSapEncapVal   TmnxEncapVal,
        tMacFilterParamsFwdSdpBind       SdpBindId,
        tMacFilterParamsTimeRangeName    TNamedItemOrEmpty,
        tMacFilterParamsTimeRangeState   TTimeRangeState,
        tMacFilterParamsRedirectURL      TmnxHttpRedirectUrl,
        tMacFilterParamsIngrHitByteCount Counter64,
        tMacFilterParamsEgrHitByteCount  Counter64,
        tMacFilterParamsLowISID          SvcISID,
        tMacFilterParamsHighISID         SvcISID,
        tMacFilterParamsInnerTagValue    QTagFullRangeOrNone,
        tMacFilterParamsInnerTagMask     QTagFullRange,
        tMacFilterParamsOuterTagValue    QTagFullRangeOrNone,
        tMacFilterParamsOuterTagMask     QTagFullRange,
        tMacFilterParamsEsi              TFilterEsi,
        tMacFilterParamsFwdEsiSvcId      TmnxServId,
        tMacFilterParamsPbrDwnActOvr     TFilterPbrDownActionOvr,
        tMacFilterParamsStickyDst        Integer32,
        tMacFilterParamsHoldRemain       Integer32,
        tMacFilterParamsDownloadAct      TFilterDownloadedAction
    }
tMacFilterParamsIndex OBJECT-TYPE
    SYNTAX      TEntryId
    MAX-ACCESS  not-accessible
    STATUS      current
    DESCRIPTION
        "This is the secondary index for the entry. Every mac filter can have
         multiple entries, therefore every mac filter entry is identified by
         the tMacFilterId and tMacFilterParamsIndex."
    ::= { tMacFilterParamsEntry 1 }

tMacFilterParamsRowStatus OBJECT-TYPE
    SYNTAX      RowStatus
    MAX-ACCESS  read-create
    STATUS      current
    DESCRIPTION
        "This object allows entries to be created and deleted in the
         tMacFilterParamsTable."
    ::= { tMacFilterParamsEntry 2 }

tMacFilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tMacFilterParamsEntry 3 }

tMacFilterParamsDescription OBJECT-TYPE
    SYNTAX      TItemDescription
    MAX-ACCESS  read-create
    STATUS      current
    DESCRIPTION
        "User-provided description for this filter entry."
    DEFVAL { ''H }
    ::= { tMacFilterParamsEntry 4 }

tMacFilterParamsAction OBJECT-TYPE
    SYNTAX      TFilterActionOrDefault
    MAX-ACCESS  read-create
    STATUS      current
    DESCRIPTION
        "The action to take for packets that match this filter entry. The value
         default(3) specifies this entry to inherit the behavior defined as the
         default for the filter. The values nat(5), reassemble(6),
         gtpLclBrkout(7) and forwardEsiL3(9) are not allowed.

         The object tMacFilterParamsAction supports only subset of filter
         actions. The object tMacFltrEntryActAction supports all actions. It's
         recommended to use tMacFltrEntryActAction instead of
         tMacFilterParamsAction.
         "
   DEFVAL { drop }
    ::= { tMacFilterParamsEntry 5 }

tMacFilterParamsFrameType OBJECT-TYPE
    SYNTAX      TFrameType
    MAX-ACCESS  read-create
    STATUS      current
    DESCRIPTION
        "The type of mac frame for which we are defining this match criteria.

         For filter entries in a MAC filter of type tMacFilterType = dot1q or
         tMacFilterType qinq the default value for this object is set to
         ethernetII (3), and no changes are allowed. In all other cases the
         default value is set to e802dot3 (0) "
    DEFVAL { e802dot3 }
    ::= { tMacFilterParamsEntry 6 }

tMacFilterParamsSrcMAC OBJECT-TYPE
    SYNTAX      MacAddress
    MAX-ACCESS  read-create
    STATUS      current
    DESCRIPTION
        "Source MAC to match for this policy MAC filter entry."
    DEFVAL { '000000000000'H }
    ::= { tMacFilterParamsEntry 8 }

tMacFilterParamsSrcMACMask OBJECT-TYPE
    SYNTAX      MacAddress
    MAX-ACCESS  read-create
    STATUS      current
    DESCRIPTION
        "Source MAC mask value for this policy MAC filter entry.
         The mask is ANDed with the MAC to match tMacFilterParamsSrcMAC.
         A cleared bit means ignore this bit, do not match. A set bit means
         match this bit with tMacFilterParamsSrcMAC.
         Use the value 00-00-00-00-00-00 to disable this filter criteria."
    DEFVAL { '000000000000'H }
    ::= { tMacFilterParamsEntry 9 }

tMacFilterParamsDstMAC OBJECT-TYPE
    SYNTAX      MacAddress
    MAX-ACCESS  read-create
    STATUS      current
    DESCRIPTION
        "Destination MAC mask value for this policy MAC filter entry."
    DEFVAL { '000000000000'H }
    ::= { tMacFilterParamsEntry 10 }

tMacFilterParamsDstMACMask OBJECT-TYPE
    SYNTAX      MacAddress
    MAX-ACCESS  read-create
    STATUS      current
    DESCRIPTION
        "Destination MAC mask value for this policy MAC filter entry.
         The mask is ANDed with the MAC to match tMacFilterParamsDstMAC.
         A cleared bit means ignore this bit, do not match. A set bit means
         match this bit with tMacFilterParamsDstMAC.
         Use the value 00-00-00-00-00-00 to disable this filter criteria."
    DEFVAL { '000000000000'H }
    ::= { tMacFilterParamsEntry 11 }

tMacFilterParamsDot1pValue OBJECT-TYPE
    SYNTAX      Dot1PPriority
    MAX-ACCESS  read-create
    STATUS      current
    DESCRIPTION
         "IEEE 802.1p priority value for this policy MAC filter entry.
      Use -1 to disable matching this filter criteria."
    DEFVAL { -1 }
    ::= { tMacFilterParamsEntry 12 }

tMacFilterParamsDot1pMask OBJECT-TYPE
    SYNTAX      Dot1PPriority (0..7)
    MAX-ACCESS  read-create
    STATUS      current
    DESCRIPTION
         "IEEE 802.1p priority mask value for this policy MAC filter entry.
          Use zero to disable matching, use 7 to match everything."
    DEFVAL { 0 }
    ::= { tMacFilterParamsEntry 13 }

tMacFilterParamsEtherType OBJECT-TYPE
    SYNTAX      INTEGER (-1 | 0..65535)
    MAX-ACCESS  read-create
    STATUS      current
    DESCRIPTION
        "Ethertype for this policy MAC filter entry. Use -1 to disable matching
         by this criteria. This object has no significance if the object
         tMacFilterParamsFrameType is not set to Ethernet_II."
    DEFVAL { -1 }
    ::= { tMacFilterParamsEntry 14 }

tMacFilterParamsDsap OBJECT-TYPE
    SYNTAX      ServiceAccessPoint
    MAX-ACCESS  read-create
    STATUS      current
    DESCRIPTION
        "MAC DSAP to match for this policy MAC filter entry. This object has no
         significance if the object tMacFilterParamsFrameType is not set to
         802dot2LLC.
         In order to reset the value to the default value, both objects
         tMacFilterParamsDsap and tMacFilterParamsDsapMask need to be modified
         together to the default value."
    DEFVAL { -1 }
    ::= { tMacFilterParamsEntry 15 }

tMacFilterParamsDsapMask OBJECT-TYPE
    SYNTAX      ServiceAccessPoint
    MAX-ACCESS  read-create
    STATUS      current
    DESCRIPTION
        "MAC DSAP mask for this policy MAC filter entry. Use 0 to disable
         matching by this criteria. This object has no significance if the
         object tMacFilterParamsFrameType is not set to 802dot2LLC.
         In order to reset the value to the default value, both objects
         tMacFilterParamsDsap and tMacFilterParamsDsapMask need to be modified
         together to the default value."
    DEFVAL { -1 }
    ::= { tMacFilterParamsEntry 16 }

tMacFilterParamsSsap OBJECT-TYPE
    SYNTAX      ServiceAccessPoint
    MAX-ACCESS  read-create
    STATUS      current
    DESCRIPTION
        "MAC SSAP to match for this policy MAC filter entry. This object has no
         significance if the object tMacFilterParamsFrameType is not set to
         802dot2LLC.
         In order to reset the value to the default value, both objects
         tMacFilterParamsSsap and tMacFilterParamsSsapMask need to be modified
         together to the default value."
    DEFVAL { -1 }
    ::= { tMacFilterParamsEntry 17 }

tMacFilterParamsSsapMask OBJECT-TYPE
    SYNTAX      ServiceAccessPoint
    MAX-ACCESS  read-create
    STATUS      current
    DESCRIPTION
        "MAC SSAP mask for this policy MAC filter entry. Use 0 to disable
         matching by this criteria. This object has no significance if the
         object tMacFilterParamsFrameType is not set to 802dot2LLC.
         In order to reset the value to the default value, both objects
         tMacFilterParamsSsap and tMacFilterParamsSsapMask need to be modified
         together to the default value."
    DEFVAL { -1 }
    ::= { tMacFilterParamsEntry 18 }

tMacFilterParamsSnapPid OBJECT-TYPE
    SYNTAX      INTEGER (-1 | 0..65535)
    MAX-ACCESS  read-create
    STATUS      current
    DESCRIPTION
         "MAC SNAP PID to match for this policy MAC filter entry.  Use -1 to
          disable matching by this criteria. This object has no significance if
          object tMacFilterParamsFrameType is not set to 802dot2SNAP."
    DEFVAL { -1 }
    ::= { tMacFilterParamsEntry 19 }

tMacFilterParamsSnapOui OBJECT-TYPE
    SYNTAX      INTEGER { off(1), zero(2), nonZero(3) }
    MAX-ACCESS  read-create
    STATUS      current
    DESCRIPTION
        "MAC SNAP OUI to match. The values zero(2) and nonZero(3) specify what
         to match. Matching can be disabled by the use of the value off(1).
         This object has no significance if the object
         tMacFilterParamsFrameType is not set to 802dot2SNAP."
    DEFVAL { off }
    ::= { tMacFilterParamsEntry 20 }

tMacFilterParamsIngressHitCount OBJECT-TYPE
    SYNTAX      Counter64
    MAX-ACCESS  read-only
    STATUS      current
    DESCRIPTION
        "This object indicates the number of times an ingress packet
         matched this entry."
    ::= { tMacFilterParamsEntry 21 }

tMacFilterParamsEgressHitCount OBJECT-TYPE
    SYNTAX      Counter64
    MAX-ACCESS  read-only
    STATUS      current
    DESCRIPTION
        "This object indicates the number of times an egress packet
         matched this entry."
    ::= { tMacFilterParamsEntry 22 }

tMacFilterParamsLogInstantiated OBJECT-TYPE
    SYNTAX      TruthValue
    MAX-ACCESS  read-only
    STATUS      current
    DESCRIPTION
        "tMacFilterParamsLogInstantiated indicates if the filter log for
         this filter entry has been instantiated or not."
    ::= { tMacFilterParamsEntry 23 }

tMacFilterParamsFwdSvcId OBJECT-TYPE
    SYNTAX      TmnxServId
    MAX-ACCESS  read-only
    STATUS      current
    DESCRIPTION
        "tMacFilterParamsFwdSvcId indicates the service id of the
         destination for this MAC filter entry. A value of 0 indicates that
         there is currently no active SAP or SDP destination."
    ::= { tMacFilterParamsEntry 24 }

tMacFilterParamsFwdSapPortId OBJECT-TYPE
    SYNTAX      TmnxPortID
    MAX-ACCESS  read-create
    STATUS      current
    DESCRIPTION
        "tMacFilterParamsFwdSapPortId specifies the sap port identity of the
         destination for this MAC filter entry. A value of 0 indicates that
         there is currently no SAP destination defined.
         A value different from 0 can only be specified if the value of
         the tMacFilterParamsAction object of this entry is 'forward'.
         In addition a non-zero value can only be given if the object
         tMacFilterParamsFwdSdpBind has a zero value.

         Note that the value of tMacFilterParamsFwdSapPortId is silently
         cleared by the system if tMacFilterParamsAction is set to
         value other than 'forward'(2), or any object related to 'forward'
         other than tMacFilterParamsFwdSvcId, tMacFilterParamsFwdSapPortId
         or tMacFilterParamsFwdSapEncapVal is set."
    DEFVAL { 0 }
    ::= { tMacFilterParamsEntry 25 }

tMacFilterParamsFwdSapEncapVal OBJECT-TYPE
    SYNTAX      TmnxEncapVal
    MAX-ACCESS  read-create
    STATUS      current
    DESCRIPTION
        "tMacFilterParamsFwdSapEncapVal specifies the sap port encap value
         of the destination SAP for this MAC filter entry.
         A value different from 0 can only be specified if
         the tMacFilterParamsFwdSapPortId object has a non zero value,
         and if the value of the tMacFilterParamsAction object of this entry
         is 'forward'. In addition a non-zero value can only be given if
         the object tMacFilterParamsFwdSdpBind has a zero value.
         A value of 0 indicates that either
         1) the sap encapsulation value is not specified when
            tMacFilterParamsFwdSapPortId and tMacFilterParamsFwdSvcId
            have valid values; or
         2) that there is no SAP destination.

         Note that the value of tMacFilterParamsFwdSapEncapVal is silently
         cleared by the system if tMacFilterParamsAction is set to
         value other than 'forward'(2), or any object related to 'forward'
         other than tMacFilterParamsFwdSvcId, tMacFilterParamsFwdSapPortId
         or tMacFilterParamsFwdSapEncapVal is set."
    DEFVAL { 0 }
    ::= { tMacFilterParamsEntry 26 }

tMacFilterParamsFwdSdpBind OBJECT-TYPE
    SYNTAX      SdpBindId
    MAX-ACCESS  read-create
    STATUS      current
    DESCRIPTION
        "tMacFilterParamsFwdSdpBind specifies the sdp bind identity of the
         destination for this MAC filter entry. A value of 0 indicates that
         there is currently no SDP binding defined.
         A value different from 0 can only be specified if the value of
         the tMacFilterParamsAction object of this entry is 'forward'.
         In addition a non-zero value can only be given if the objects
         tMacFilterParamsFwdSapPortId and tMacFilterParamsFwdSapEncapVal
         have a zero value.

         Note that the value of tMacFilterParamsFwdSdpBind is silently cleared
         by the system if tMacFilterParamsAction is set to
         value other than 'forward'(2), or any object related to 'forward'
         other than tMacFilterParamsFwdSvcId or tMacFilterParamsFwdSdpBind
         is set."
    DEFVAL { '0000000000000000'H }
    ::= { tMacFilterParamsEntry 27 }

tMacFilterParamsTimeRangeName OBJECT-TYPE
    SYNTAX      TNamedItemOrEmpty
    MAX-ACCESS  read-create
    STATUS      obsolete
    DESCRIPTION
        "tMacFilterParamsTimeRangeName specifies the tmnxTimeRangeEntry to be
         associated with this filter entry.

         A value for this object can only be specified during row creation, and
         cannot be altered later on.
         Also, a value is accepted only if the tmnxTimeRangeEntry is defined in
         the TIMETRA-SCHEDULER-MIB::tmnxTimeRangeTable.tTimeRangeName.

         This object is obsoleted in release 14.0."
    DEFVAL { ''H }
    ::= { tMacFilterParamsEntry 28 }

tMacFilterParamsTimeRangeState OBJECT-TYPE
    SYNTAX      TTimeRangeState
    MAX-ACCESS  read-only
    STATUS      obsolete
    DESCRIPTION
        "tMacFilterParamsTimeRangeState indicates whether or not the entry
         is currently in effect.
         - timeRangeNotApplic:
           no time range is applicable for this entry.
         - timeRangeNotActive:
           A time range is defined in tMacFilterParamsTimeRangeName, but is not
           active at this moment. Consequently the filter entry is not
           installed.
         - timeRangeActive.
           A time range is defined in tMacFilterParamsTimeRangeName, and is
           activated successfully.
         - timeRangeActiveDownloadFailed:
           A time range is defined in tMacFilterParamsTimeRangeName, and is
           activated, but the corresponding filter entry could not be
           installed due to resource problems.

         This object is obsoleted in release 14.0."
    ::= { tMacFilterParamsEntry 29 }

tMacFilterParamsRedirectURL OBJECT-TYPE
    SYNTAX      TmnxHttpRedirectUrl
    MAX-ACCESS  read-create
    STATUS      current
    DESCRIPTION
        "The value of tMacFilterParamsRedirectURL specifies the URL
         to redirect to, when the value of tMacFilterParamsAction is
         'httpRedirect'.

         Note that the value of tMacFilterParamsRedirectURL is silently
         cleared by the system if tMacFilterParamsAction is set to any value
         other than 'httpRedirect'."
    DEFVAL { ''H }
    ::= { tMacFilterParamsEntry 30 }

tMacFilterParamsIngrHitByteCount OBJECT-TYPE
    SYNTAX      Counter64
    MAX-ACCESS  read-only
    STATUS      current
    DESCRIPTION
        "The value of tMacFilterParamsIngrHitByteCount indicates the number
         of bytes of all ingress packets that matched this entry."
    ::= { tMacFilterParamsEntry 31 }

tMacFilterParamsEgrHitByteCount OBJECT-TYPE
    SYNTAX      Counter64
    MAX-ACCESS  read-only
    STATUS      current
    DESCRIPTION
        "The value of tMacFilterParamsEgrHitByteCount indicates the number
         of bytes of all egress packets that matched this entry."
    ::= { tMacFilterParamsEntry 32 }

tMacFilterParamsLowISID OBJECT-TYPE
    SYNTAX      SvcISID
    MAX-ACCESS  read-create
    STATUS      current
    DESCRIPTION
        "The value of tMacFilterParamsLowISID specifies the lowest value of the
         24 bit (0..16777215) service instance identifier for this service that
         matches this entry.

         The default value of -1 indicates no ISID matching will be performed.

         The value of this field can be equal to but not lower than the value
         of the tMacFilterParamsHighISID field.

         Changing the value of this field might also change the value of
         tMacFilterParamsHighISID:
         A value of -1 will change the value of tMacFilterParamsHighISID to -1.
         Changing the value of this field from -1 to any other value will change
         the value of tMacFilterParamsHighISID to this same value.

         Note that tMacFilterParamsLowISID and tMacFilterParamsHighISID can only
         be set if tMacFilterType is set to 'isid(1)'."
    DEFVAL { -1 }
    ::= { tMacFilterParamsEntry 33 }

tMacFilterParamsHighISID OBJECT-TYPE
    SYNTAX      SvcISID
    MAX-ACCESS  read-create
    STATUS      current
    DESCRIPTION
        "The value of tMacFilterParamsHighISID specifies the highest value of
         the 24 bit (0..16777215) service instance identifier for this service
         that matches this entry.

         The default value of -1 indicates no ISID matching will be performed.

         The value of this field can be equal to but not higher than the value
         of the tMacFilterParamsLowISID field.

         Changing the value of this field might also change the value of
         tMacFilterParamsLowISID:
         A value of -1 will change the value of tMacFilterParamsLowISID to -1.
         Changing the value of this field from -1 to any other value will change
         the value of tMacFilterParamsLowISID to this same value.

         Note that tMacFilterParamsLowISID and tMacFilterParamsHighISID can only
         be set if tMacFilterType is set to 'isid(1)'."
    DEFVAL { -1 }
    ::= { tMacFilterParamsEntry 34 }

tMacFilterParamsInnerTagValue OBJECT-TYPE
    SYNTAX      QTagFullRangeOrNone
    MAX-ACCESS  read-create
    STATUS      current
    DESCRIPTION
        "The value of tMacFilterParamsInnerTagValue specifies the value to match
         against the VID of the second VLAN tag in the packet that
         is carried transparently through the service (the second vlan tag after
         the service delimiting tags).

         This object can only be set if tMacFilterType is set to 'vid(3)'.

         The (default) value of '-1' indicates no inner VLAN tag matching will
         be performed."
    DEFVAL { -1 }
    ::= { tMacFilterParamsEntry 35 }

tMacFilterParamsInnerTagMask OBJECT-TYPE
    SYNTAX      QTagFullRange (1..4095)
    MAX-ACCESS  read-create
    STATUS      current
    DESCRIPTION
        "The value of tMacFilterParamsInnerTagMask is applied as a mask to VID
         of the inner VLAN tag of the packet prior to comparing it
         with tMacFilterParamsInnerTagValue.  The inner tag is the second tag in
         the packet that is carried transparently through the service
         (the second tag after the service delimiting tags).

         This object can only be set if tMacFilterType is set to 'vid(3)'."
    DEFVAL { 4095 } -- 0xFFF : all ones mask.
    ::= { tMacFilterParamsEntry 36 }

tMacFilterParamsOuterTagValue OBJECT-TYPE
    SYNTAX      QTagFullRangeOrNone
    MAX-ACCESS  read-create
    STATUS      current
    DESCRIPTION
        "The value of tMacFilterParamsOuterTagValue specifies the value to match
         against the VID of the first VLAN tag in the packet that
         is carried transparently through the service (the first vlan tag after
         the service delimiting tags).

         This object can only be set if tMacFilterType is set to 'vid(3)'.

         The (default) value of '-1' indicates no outer VLAN tag matching will
         be performed."
    DEFVAL { -1 }
    ::= { tMacFilterParamsEntry 37 }

tMacFilterParamsOuterTagMask OBJECT-TYPE
    SYNTAX      QTagFullRange (1..4095)
    MAX-ACCESS  read-create
    STATUS      current
    DESCRIPTION
        "The value of tMacFilterParamsOuterTagMask is applied as a mask to VID
         of the outer VLAN tag of the packet prior to comparing it
         with tMacFilterParamsOuterTagValue.  The outer tag is the first tag in
         the packet that is carried transparently through the service
         (the first tag after the service delimiting tags).

         This object can only be set if tMacFilterType is set to 'vid(3)'."
    DEFVAL { 4095 } -- 0xFFF : all ones mask.
    ::= { tMacFilterParamsEntry 38 }

tMacFilterParamsEsi OBJECT-TYPE
    SYNTAX      TFilterEsi
    MAX-ACCESS  read-create
    STATUS      current
    DESCRIPTION
        "The value of the object tMacFilterParamsEsi specifies the ethernet
         segment identifier (ESI) of the first ESI identified appliance in Nuage
         service chain. When the value of tMacFilterParamsAction is
         'forwardEsiL2' packets matching the filter entry are forwarded to the
         appliance using EVPN-resolved VXLAN tunnel in the specified VPLS
         service (tMacFilterParamsFwdEsiSvcId).

         The value '0' indicates that there is no ESI specified. The value of
         tMacFilterParamsEsi is ignored by the system if the value of
         tMacFilterParamsAction is different from 'forwardEsiL2'. The value of
         tMacFilterParamsAction can be set to 'forwardEsiL2' only if
         tMacFilterParamsEsi and tMacFilterParamsFwdEsiSvcId are set to non zero
         values."
    DEFVAL { '00000000000000000000'H }
    ::= { tMacFilterParamsEntry 39 }

tMacFilterParamsFwdEsiSvcId OBJECT-TYPE
    SYNTAX      TmnxServId
    MAX-ACCESS  read-create
    STATUS      current
    DESCRIPTION
        "The value of the object tMacFilterParamsFwdEsiSvcId specifies the
         identifier of the VPLS used for VPN/DC connectivity.

         The value '0' indicates that no VPLS identifier is specified. The
         value of tMacFilterParamsFwdEsiSvcId is ignored by the system if the
         value of tMacFilterParamsAction is different from 'forwardEsiL2'. The
         value of tMacFilterParamsAction can be set to 'forwardEsiL2' only if
         tMacFilterParamsEsi and tMacFilterParamsFwdEsiSvcId are set to non zero
         values."
    DEFVAL { 0 }
    ::= { tMacFilterParamsEntry 40 }

tMacFilterParamsPbrDwnActOvr OBJECT-TYPE
    SYNTAX      TFilterPbrDownActionOvr
    MAX-ACCESS  read-create
    STATUS      current
    DESCRIPTION
        "The value of the object tMacFilterParamsPbrDwnActOvr specifies the
         filter action which will be performed when the PBR/PBF target for this
         entry is not available.

         If the value of tMacFltrEntryActAction is not one of the following
         values then tMacFilterParamsPbrDwnActOvr must be set to the value
         'none':
         - forwardEsiL2
         - forwardSap
         - forwardSdp

         If the value of tMacFilterParamsPbrDwnActOvr is different from 'none'
         then PBF destination availability checking for an entry is turned on.
         There is a limit to the number of filter entries with the destination
         availability checking turned on. Entries with the value of
         tMacFltrEntryActAction equal to 'forwardEsiL2' are not counted against
         this limit.

         Refer to the description of the textual convention
         TFilterPbrDownActionOvr for more details."
    DEFVAL { none }
    ::= { tMacFilterParamsEntry 41 }

tMacFilterParamsStickyDst OBJECT-TYPE
    SYNTAX      Integer32 (-1|0..65535)
    UNITS       "seconds"
    MAX-ACCESS  read-create
    STATUS      current
    DESCRIPTION
        "The value of the object tMacFilterParamsStickyDst specifies how long
         the system will wait (in seconds) until it activates the best action
         (action with available PBF destination and the highest priority).
         Until then the action specified by tMacFilterParamsPbrDwnActOvr will
         be taken on a packet matching the filter entry. After the value of the
         active destination is fixed it will remain unchanged until the active
         PBF destination becomes unreachable.

         The value of -1 indicates that the property of PBF destination
         stickiness is turned off. When the property of stickiness is turned off
         the active PBF destination is always the one which is available and
         has the highest priority.

         The countdown starts when there was no PBR/PBF destination reachable
         and any PBR/PBF destination becomes reachable.

         tMacFilterParamsStickyDst can be set to value other than -1 only if
         the value of tMacFltrEntryActAction is 'forwardSap' or 'forwardSdp'."
    DEFVAL { -1 }
    ::= { tMacFilterParamsEntry 42 }

tMacFilterParamsHoldRemain OBJECT-TYPE
    SYNTAX      Integer32 (0..65535)
    MAX-ACCESS  read-only
    STATUS      current
    DESCRIPTION
        "The value of the object tMacFilterParamsHoldRemain indicates the
         remaining time in seconds, until the best action will become active
         and will be fixed.

         Best action is:
         - primary action if PBR target status of primary action is up.
         - secondary action if PBR target status of secondary action is up
           and PBR target status of primary action is down.
         - none if both PBR targets are down
         "
    ::= { tMacFilterParamsEntry 43 }

tMacFilterParamsDownloadAct OBJECT-TYPE
    SYNTAX      TFilterDownloadedAction
    MAX-ACCESS  read-only
    STATUS      current
    DESCRIPTION
        "The value of the object tMacFilterParamsDownloadAct indicates
         the filter entry action downloaded to IOM.

         Refer to the description of the textual convention
         TFilterDownloadedAction for more information."
    ::= { tMacFilterParamsEntry 44 }
--
-- Filter Log table
--

tFilterLogTable OBJECT-TYPE
    SYNTAX      SEQUENCE OF TFilterLogEntry
    MAX-ACCESS  not-accessible
    STATUS      current
    DESCRIPTION  "A table of all filter logs."
    ::= { tFilterObjects 5 }

tFilterLogEntry OBJECT-TYPE
    SYNTAX      TFilterLogEntry
    MAX-ACCESS  not-accessible
    STATUS      current
    DESCRIPTION
        "Information about a particular Filter Log entry."
    INDEX { tFilterLogId }
    ::= { tFilterLogTable 1 }

TFilterLogEntry ::= SEQUENCE
    {
        tFilterLogId              TFilterLogId,
        tFilterLogRowStatus       RowStatus,
        tFilterLogDestination     TFilterLogDestination,
        tFilterLogDescription     TItemDescription,
        tFilterLogMaxNumEntries   Unsigned32,
        tFilterLogSysLogId        Unsigned32,
        tFilterLogFileId          Unsigned32,
        tFilterLogStopOnFull      TruthValue,
        tFilterLogEnabled         TruthValue,
        tFilterLogSummaryEnabled  TruthValue,
        tFilterLogSummaryCrit1    TFilterLogSummaryCriterium
    }

tFilterLogId OBJECT-TYPE
    SYNTAX      TFilterLogId
    MAX-ACCESS  not-accessible
    STATUS      current
    DESCRIPTION
        "This is the index for the entry. An entry cannot be created with an
        id of 0."
    ::= { tFilterLogEntry 1 }

tFilterLogRowStatus OBJECT-TYPE
    SYNTAX      RowStatus
    MAX-ACCESS  read-create
    STATUS      current
    DESCRIPTION
        "This object allows entries to be created and deleted in the
         tFilterLogTable."
    ::= { tFilterLogEntry 2 }

tFilterLogDestination OBJECT-TYPE
    SYNTAX      TFilterLogDestination
    MAX-ACCESS  read-create
    STATUS      current
    DESCRIPTION
        "This object specifies the destination of the log."
    DEFVAL { memory }
    ::= { tFilterLogEntry 3 }

tFilterLogDescription OBJECT-TYPE
    SYNTAX      TItemDescription
    MAX-ACCESS  read-create
    STATUS      current
    DESCRIPTION
        "User-provided description for this filter log entry."
    DEFVAL { ''H }
    ::= { tFilterLogEntry 4 }

tFilterLogMaxNumEntries OBJECT-TYPE
    SYNTAX      Unsigned32 (0..50000)
    MAX-ACCESS  read-create
    STATUS      current
    DESCRIPTION
        "The object tFilterLogMaxNumEntries specifies the maximum number
         of entries that the log can store.

         If tFilterLogDestination is not 'memory(1)' then
         the object tFilterLogMaxNumEntries maintains a value of '0',
         and Any change attempts will be silently discarded."
    DEFVAL { 1000 }
    ::= { tFilterLogEntry 5 }

tFilterLogSysLogId OBJECT-TYPE
    SYNTAX      Unsigned32
    MAX-ACCESS  read-create
    STATUS      current
    DESCRIPTION
        "The object tFilterLogSysLogId specifies the syslog Id to be used
         as destination.

         If tFilterLogDestination is not 'sysLog(2)' then the object
         tFilterLogSysLogId maintains a value of '0',
         and any change attempts will be silently discarded."
    DEFVAL { 0 }
    ::= { tFilterLogEntry 6 }

tFilterLogFileId OBJECT-TYPE
    SYNTAX      Unsigned32
    MAX-ACCESS  read-create
    STATUS      current
    DESCRIPTION
        "The object tFilterLogFileId specifies the File Id to be used
         as destination.

         If tFilterLogDestination is not 'file(3)' then the object
         tFilterLogFileId maintains a value of '0',
         and any change attempts will be silently discarded."
    DEFVAL { 0 }
    ::= { tFilterLogEntry 7 }

tFilterLogStopOnFull OBJECT-TYPE
    SYNTAX      TruthValue
    MAX-ACCESS  read-create
    STATUS      current
    DESCRIPTION
        ""
    DEFVAL { false }
    ::= { tFilterLogEntry 8 }

tFilterLogEnabled OBJECT-TYPE
    SYNTAX      TruthValue
    MAX-ACCESS  read-create
    STATUS      current
    DESCRIPTION
        ""
    DEFVAL { true }
    ::= { tFilterLogEntry 9 }

tFilterLogSummaryEnabled OBJECT-TYPE
    SYNTAX      TruthValue
    MAX-ACCESS  read-create
    STATUS      current
    DESCRIPTION
         "The value of tFilterLogSummaryEnabled specifies whether
          or not summarization of filter log entries is performed.
          Summarization is only allowed in case tFilterLogDestination is set
          to syslog."
    DEFVAL { false }
    ::= { tFilterLogEntry 10 }

tFilterLogSummaryCrit1 OBJECT-TYPE
    SYNTAX      TFilterLogSummaryCriterium
    MAX-ACCESS  read-create
    STATUS      current
    DESCRIPTION
        "The value of tFilterLogSummaryCrit1 specifies how
         filter log entries will be summarized.

         This field is only meaningful if the object
         tFilterLogSummaryEnabled is set to true."
    DEFVAL { srcAddr }
    ::= { tFilterLogEntry 11 }

--
-- Filter Log Scalars
--

tFilterLogScalars  OBJECT IDENTIFIER ::= { tFilterObjects 6 }

tFilterLogMaxInstances OBJECT-TYPE
    SYNTAX      Gauge32
    MAX-ACCESS  read-only
    STATUS      current
    DESCRIPTION
        "tFilterLogMaxInstances maintains the maximum allowed instances
         of filter logs allowed on the system"
    ::= { tFilterLogScalars 1 }

tFilterLogInstances OBJECT-TYPE
    SYNTAX      Gauge32
    MAX-ACCESS  read-only
    STATUS      current
    DESCRIPTION
        "tFilterLogInstances maintains the instances of filter logs
         presently existing on the system"
    ::= { tFilterLogScalars 2 }

tFilterLogBindings OBJECT-TYPE
    SYNTAX      Gauge32
    MAX-ACCESS  read-only
    STATUS      current
    DESCRIPTION
        "tFilterLogBindings maintains the count of the configured
         filter log bindings presently existing on the system. The
         bindings get instantiated when the filter is instantiated"
    ::= { tFilterLogScalars 3 }


--
-- Filter Redirect Policies
--

tFilterRedirectPolicyTable OBJECT-TYPE
    SYNTAX      SEQUENCE OF TFilterRedirectPolicyEntry
    MAX-ACCESS  not-accessible
    STATUS      current
    DESCRIPTION
        "Contains a List of all redirect policies configured on this system."
    ::= { tFilterObjects 10 }

tFilterRedirectPolicyEntry OBJECT-TYPE
    SYNTAX      TFilterRedirectPolicyEntry
    MAX-ACCESS  not-accessible
    STATUS      current
    DESCRIPTION
        "Information about a particular redirect policy. Entries are
        created/deleted by user."
    INDEX { tFilterRedirectPolicy }
    ::= { tFilterRedirectPolicyTable 1 }

TFilterRedirectPolicyEntry ::= SEQUENCE
    {
        tFilterRedirectPolicy         TNamedItem,
        tFilterRPRowStatus            RowStatus,
        tFilterRPDescription          TItemDescription,
        tFilterRPAdminState           TmnxAdminState,
        tFilterRPActiveDest           IpAddress,
        tFilterRPVrtrId               TmnxVRtrIDOrZero,
        tFilterRPActiveDestAddrType   InetAddressType,
        tFilterRPActiveDestAddr       InetAddress,
        tFilterRPDstStickiness        Integer32,
        tFilterRPBestDstAddrType      InetAddressType,
        tFilterRPBestDstAddr          InetAddress,
        tFilterRPStickinessHoldRemain Integer32
    }

tFilterRedirectPolicy OBJECT-TYPE
    SYNTAX      TNamedItem
    MAX-ACCESS  not-accessible
    STATUS      current
    DESCRIPTION
        "tFilterRedirectPolicy uniquely identifies each redirect policy
        configured on this system."
    ::= { tFilterRedirectPolicyEntry 1 }

tFilterRPRowStatus OBJECT-TYPE
    SYNTAX      RowStatus
    MAX-ACCESS  read-create
    STATUS      current
    DESCRIPTION
        "tFilterRPRowStatus allows entries to be created and deleted in the
        tFilterRedirectPolicyTable."
    ::= { tFilterRedirectPolicyEntry 2 }

tFilterRPDescription OBJECT-TYPE
    SYNTAX      TItemDescription
    MAX-ACCESS  read-create
    STATUS      current
    DESCRIPTION
        "User-provided description for this redirect policy is maintained in
        the object tFilterRPDescription."
    DEFVAL { ''H }
    ::= { tFilterRedirectPolicyEntry 3 }

tFilterRPAdminState OBJECT-TYPE
    SYNTAX      TmnxAdminState
    MAX-ACCESS  read-create
    STATUS      current
    DESCRIPTION
        "tFilterRPAdminState holds the admin state of the policy. If the
        admin state is 'outOfService', the tests will not be conducted."
    DEFVAL { outOfService }
    ::= { tFilterRedirectPolicyEntry 4 }

tFilterRPActiveDest OBJECT-TYPE
    SYNTAX      IpAddress
    MAX-ACCESS  read-only
    STATUS      obsolete
    DESCRIPTION
        "tFilterRPActiveDest indicates the IP address of the active
        destination. A value of 0 indicates that there is currently
        no active destination.

        This object is obsoleted in release 13.0."
    ::= { tFilterRedirectPolicyEntry 5 }

tFilterRPVrtrId OBJECT-TYPE
    SYNTAX     TmnxVRtrIDOrZero
    MAX-ACCESS read-create
    STATUS     current
    DESCRIPTION
        "The value of the object tFilterRPVrtrId specifies the target routing
        instance as part of the redirect policy. When the target routing
        instance is configured (not equal to 0), the following applies:

        - Ping and unicast-reachability tests configured in a redirect policy
          are now executed in the routing instance specified by the redirect
          policy regardless of what routing instance is the filter using this
          redirect policy deployed in.

        - When packets are routed to a destination configured in a redirect
          policy with router instance specified (as result of filter match),
          routing is executed in the router instance context configured in
          the redirect policy regardless of the routing context for the
          interface on which the packet arrived.
          Note that if all destinations are down, the forward action is still
          executed in the routing instance of the incoming interface and not
          the routing instance of the redirect policy.
          If PBR specifies action forward router, then deploying the policy
          on card not supporting such action will result in action forward
          using incoming interface routing context.

        - If the H/W does not support the next-hop router PBR action, action
          forward is executed (even if the router instance in the action is the
          same as the router instance of the incoming interface).

        If the target routing instance is not configured (equal to 0),
        the following applies:

        - Redirect policy can be deployed in any VPRN or GRT routing context
          but a test will only run in GRT context regardless of where the policy
          is deployed.

        - The PBR will execute in the routing context of the ingress interface.

        SNMP and URL tests can be configured only if the target routing instance
        is not configured."
    DEFVAL { 0 }
    ::= { tFilterRedirectPolicyEntry 6 }

tFilterRPActiveDestAddrType OBJECT-TYPE
    SYNTAX      InetAddressType
    MAX-ACCESS  read-only
    STATUS      current
    DESCRIPTION
        "The value of the object tFilterRPActiveDestAddrType indicates
         the context in which the values of the objects tFilterRPActiveDestAddr
         are interpreted.

         Only following values are supported:
            unknown(0)
            ipv4(1)
            ipv6(2)
        "
    DEFVAL { unknown }
    ::= { tFilterRedirectPolicyEntry 7 }

tFilterRPActiveDestAddr OBJECT-TYPE
    SYNTAX      InetAddress (SIZE (0|4|16))
    MAX-ACCESS  read-only
    STATUS      current
    DESCRIPTION
        "The value of the object tFilterRPActiveDestAddr indicates the IP
        address of the active destination. A value of 0 indicates that
        there is currently no active destination.

        The value must be consistent with the IP version value of
        the associated tFilterRPActiveDestAddrType object."
    DEFVAL { ''H }
    ::= { tFilterRedirectPolicyEntry 8 }

tFilterRPDstStickiness OBJECT-TYPE
    SYNTAX      Integer32 (-1|0..65535)
    UNITS       "seconds"
    MAX-ACCESS  read-create
    STATUS      current
    DESCRIPTION
        "The value of the object tFilterRPDstStickiness specifies the time in
         seconds, how long the system will wait until it sets and fixes the
         current best destination as active destination.  After the value of
         active destination is fixed it will remain unchanged until the active
         destination becomes unreachable.

         When the value of tFilterRPDstStickiness is -1 the property of
         destination stickiness is turned off. That means that active
         destination is always the best one.

         The countdown starts when there was no destination reachable and any
         destination becomes reachable."
    DEFVAL { -1 }
    ::= { tFilterRedirectPolicyEntry 9 }

tFilterRPBestDstAddrType OBJECT-TYPE
    SYNTAX      InetAddressType
    MAX-ACCESS  read-only
    STATUS      current
    DESCRIPTION
        "The value of the object tFilterRPBestDstAddrType indicates
         the context in which the values of the objects tFilterRPActiveDestAddr
         are interpreted.

         Only following values are supported:
            unknown(0)
            ipv4(1)
            ipv6(2)
        "
    DEFVAL { unknown }
    ::= { tFilterRedirectPolicyEntry 10 }

tFilterRPBestDstAddr OBJECT-TYPE
    SYNTAX      InetAddress (SIZE (0|4|16))
    MAX-ACCESS  read-only
    STATUS      current
    DESCRIPTION
        "The value of the object tFilterRPBestDstAddr indicates the IP address
         of the available destination with the highest priority.  A value of
         0 indicates that currently there is no reachable destination.

         The value must be consistent with the IP version value of the
         associated tFilterRPActiveDestAddrType object."
    DEFVAL { ''H }
    ::= { tFilterRedirectPolicyEntry 11 }

tFilterRPStickinessHoldRemain OBJECT-TYPE
    SYNTAX      Integer32 (0..65535)
    MAX-ACCESS  read-only
    STATUS      current
    DESCRIPTION
        "The value of the object tFilterRPStickinessHoldRemain indicates the
         remaining time in seconds, until the best destination becomes the
         active destination and will become fixed."
    DEFVAL { 0 }
    ::= { tFilterRedirectPolicyEntry 12 }

--
-- Filter Redirect Destinations
--

tFilterRedirectDestTable OBJECT-TYPE
    SYNTAX      SEQUENCE OF TFilterRedirectDestEntry
    MAX-ACCESS  not-accessible
    STATUS      obsolete
    DESCRIPTION
        "Contains a List of all redirect destinations configured on this
        system.

        This table is obsoleted in release 13.0 and replaced by
        tFilterRPlcyDstTable."
    ::= { tFilterObjects 11 }

tFilterRedirectDestEntry OBJECT-TYPE
    SYNTAX      TFilterRedirectDestEntry
    MAX-ACCESS  not-accessible
    STATUS      obsolete
    DESCRIPTION
        "Information about a particular Redirect destination. Entries are
         created/deleted by user.

         This object is obsoleted in release 13.0."
    INDEX { tFilterRedirectPolicy, tFilterRedirectDest }
    ::= { tFilterRedirectDestTable 1 }

TFilterRedirectDestEntry ::= SEQUENCE
    {
        tFilterRedirectDest       IpAddress,
        tFilterRDRowStatus        RowStatus,
        tFilterRDDescription      TItemDescription,
        tFilterRDAdminPriority    Unsigned32,
        tFilterRDOperPriority     Unsigned32,
        tFilterRDAdminState       TmnxAdminState,
        tFilterRDOperState        TmnxOperState
    }

tFilterRedirectDest OBJECT-TYPE
    SYNTAX      IpAddress
    MAX-ACCESS  not-accessible
    STATUS      obsolete
    DESCRIPTION
        "tFilterRedirectDest holds the IP address of the destination
        entry.

        This object is obsoleted in release 13.0."
    ::= { tFilterRedirectDestEntry 1 }

tFilterRDRowStatus OBJECT-TYPE
    SYNTAX      RowStatus
    MAX-ACCESS  read-create
    STATUS      obsolete
    DESCRIPTION
        "tFilterRDRowStatus allows entries to be created and deleted
        in the tFilterRedirectDestTable.

        This object is obsoleted in release 13.0."
    ::= { tFilterRedirectDestEntry 2 }

tFilterRDDescription OBJECT-TYPE
    SYNTAX      TItemDescription
    MAX-ACCESS  read-create
    STATUS      obsolete
    DESCRIPTION
        "User-provided description for this destination is maintained in
        the object tFilterRDDescription.

        This object is obsoleted in release 13.0."
    DEFVAL { ''H }
    ::= { tFilterRedirectDestEntry 3 }

tFilterRDAdminPriority OBJECT-TYPE
    SYNTAX      Unsigned32 (1..255)
    MAX-ACCESS  read-create
    STATUS      obsolete
    DESCRIPTION
        "tFilterRDAdminPriority holds the configured base priority for
        the destination.

        This object is obsoleted in release 13.0."
    DEFVAL { 100 }
    ::= { tFilterRedirectDestEntry 4 }

tFilterRDOperPriority OBJECT-TYPE
    SYNTAX      Unsigned32 (0..255)
    MAX-ACCESS  read-only
    STATUS      obsolete
    DESCRIPTION
        "tFilterRDAdminPriority maintains the operational value of the
        priority for this destination. The highest operational priority
        across multiple destinations is used as the preferred destination.

        A value of '0' is maintained if the destination if tFilterRDOperState
        is 'outOfService'.

        This object is obsoleted in release 13.0."
    ::= { tFilterRedirectDestEntry 5 }

tFilterRDAdminState OBJECT-TYPE
    SYNTAX      TmnxAdminState
    MAX-ACCESS  read-create
    STATUS      obsolete
    DESCRIPTION
        "tFilterRDAdminState maintains the configured state of the destination.
        If the admin state is 'outOfService', the tests for this destination
        will not be conducted.

        This object is obsoleted in release 13.0."
    DEFVAL { outOfService }
    ::= { tFilterRedirectDestEntry 6 }

tFilterRDOperState OBJECT-TYPE
    SYNTAX      TmnxOperState
    MAX-ACCESS  read-only
    STATUS      obsolete
    DESCRIPTION
        "The value of tFilterRDOperState indicates the operational state of
         the destination.

         This object is obsoleted in release 13.0."
    ::= { tFilterRedirectDestEntry 7 }

--
-- Filter Redirect SNMP Test Table
--

tFilterRedirectSNMPTestTable OBJECT-TYPE
    SYNTAX      SEQUENCE OF TFilterRedirectSNMPTestEntry
    MAX-ACCESS  not-accessible
    STATUS      obsolete
    DESCRIPTION
        "Contains a List of all redirect SNMP tests configured on this
        system.

        This table is obsoleted in release 13.0 and replaced by
        tFilterRPlcySNMPTestTable."
    ::= { tFilterObjects 12 }

tFilterRedirectSNMPTestEntry OBJECT-TYPE
    SYNTAX      TFilterRedirectSNMPTestEntry
    MAX-ACCESS  not-accessible
    STATUS      obsolete
    DESCRIPTION
        "Information about a specific SNMP test configured for a destination.
        Entries are created/deleted  by user.

        This object is obsoleted in release 13.0."
    INDEX {
              tFilterRedirectPolicy,
              tFilterRedirectDest,
              tFilterRedirectSNMPTest
          }
    ::= { tFilterRedirectSNMPTestTable 1 }

TFilterRedirectSNMPTestEntry ::= SEQUENCE
    {
        tFilterRedirectSNMPTest       TNamedItem,
        tFilterRSTRowStatus           RowStatus,
        tFilterRSTOID                 OBJECT IDENTIFIER,
        tFilterRSTCommunity           DisplayString,
        tFilterRSTSNMPVersion         INTEGER,
        tFilterRSTInterval            Unsigned32,
        tFilterRSTTimeout             Unsigned32,
        tFilterRSTDropCount           Unsigned32,
        tFilterRSTHoldDown            Unsigned32,
        tFilterRSTHoldDownRemain      Unsigned32,
        tFilterRSTLastActionTime      TimeStamp,
        tFilterRSTLastOID             OBJECT IDENTIFIER,
        tFilterRSTLastType            INTEGER,
        tFilterRSTLastCounter32Val    Counter32,
        tFilterRSTLastUnsigned32Val   Unsigned32,
        tFilterRSTLastTimeTicksVal    TimeTicks,
        tFilterRSTLastInt32Val        Integer32,
        tFilterRSTLastOctetStringVal  OCTET STRING,
        tFilterRSTLastIpAddressVal    IpAddress,
        tFilterRSTLastOidVal          OBJECT IDENTIFIER,
        tFilterRSTLastCounter64Val    Counter64,
        tFilterRSTLastOpaqueVal       Opaque,
        tFilterRSTLastAction          INTEGER,
        tFilterRSTLastPrioChange      Integer32,
        tFilterRSTNextRespIndex       Integer32
    }

tFilterRedirectSNMPTest OBJECT-TYPE
    SYNTAX      TNamedItem
    MAX-ACCESS  not-accessible
    STATUS      obsolete
    DESCRIPTION
        "tFilterRedirectSNMPTest specifies the name of the SNMP test.

        This object is obsoleted in release 13.0."
    ::= { tFilterRedirectSNMPTestEntry 1 }

tFilterRSTRowStatus OBJECT-TYPE
    SYNTAX      RowStatus
    MAX-ACCESS  read-create
    STATUS      obsolete
    DESCRIPTION
        "tFilterRSTRowStatus allows tests to be created and deleted in the
         tFilterRedirectSNMPTestTable.

         This object is obsoleted in release 13.0."
    ::= { tFilterRedirectSNMPTestEntry 2 }

tFilterRSTOID OBJECT-TYPE
    SYNTAX      OBJECT IDENTIFIER
    MAX-ACCESS  read-create
    STATUS      obsolete
    DESCRIPTION
        "tFilterRSTOID stores the OID of the object to be fetched from the
        destination.
        The value of this object can only be changed if the object
        tFilterRSTCommunity is changed at the same time.

        This object is obsoleted in release 13.0."
    ::= { tFilterRedirectSNMPTestEntry 3 }

tFilterRSTCommunity OBJECT-TYPE
    SYNTAX      DisplayString (SIZE(0..32))
    MAX-ACCESS  read-create
    STATUS      obsolete
    DESCRIPTION
        "The value of tFilterRSTCommunity is the SNMPv1 or SNMPv2c Community
         String or the SNMPv3 Context Name used to conduct this SNMP test as
         described in RFC2571 and RFC2737.

         When the value of tFilterRSTSNMPVersion is 'snmpv1' or 'snmpv2c'
         this object represents a community string.  When the value of
         tFilterRSTSNMPVersion is 'snmpv3' this object represents a SNMPv3
         context name.
         The value of this object can only be changed if the object
         tFilterRSTOID is changed at the same time.

         This object is obsoleted in release 13.0."
    DEFVAL { ''H }
    ::= { tFilterRedirectSNMPTestEntry 4 }

tFilterRSTSNMPVersion OBJECT-TYPE
    SYNTAX      INTEGER {
                     snmpv1 (1),
                     snmpv2c (2),
                     snmpv3 (3)
                 }
    MAX-ACCESS  read-create
    STATUS      obsolete
    DESCRIPTION
        "tFilterRSTSNMPVersion specifies the SNMP PDU format to be used while
         conducting the test. Currently only snmpv2c is supported.

         This object is obsoleted in release 13.0."
    DEFVAL { snmpv2c }
    ::= { tFilterRedirectSNMPTestEntry 5 }

tFilterRSTInterval OBJECT-TYPE
    SYNTAX      Unsigned32 (1..60)
    UNITS        "seconds"
    MAX-ACCESS  read-create
    STATUS      obsolete
    DESCRIPTION
        "The value of tFilterRSTInterval specifies the amount of time
        in seconds between consecutive requests sent to the far end
        host.

        This object is obsoleted in release 13.0."
    DEFVAL { 1 }
    ::= { tFilterRedirectSNMPTestEntry 6 }

tFilterRSTTimeout OBJECT-TYPE
    SYNTAX      Unsigned32 (1..60)
    UNITS        "seconds"
    MAX-ACCESS  read-create
    STATUS      obsolete
    DESCRIPTION
        "The value of tFilterRSTTimeout specifies the amount of time
        in seconds that is allowed for receiving a response from the
        far end host. If a reply is not received within this time the
        far end host is considered unresponsive.

        This object is obsoleted in release 13.0."
    DEFVAL { 1 }
    ::= { tFilterRedirectSNMPTestEntry 7 }

tFilterRSTDropCount OBJECT-TYPE
    SYNTAX      Unsigned32 (1..60)
    MAX-ACCESS  read-create
    STATUS      obsolete
    DESCRIPTION
        "The value of tFilterRSTDropCount specifies the number of
        consecutive requests that must fail for the destination to
        declared unreachable.

        This object is obsoleted in release 13.0."
    DEFVAL { 3 }
    ::= { tFilterRedirectSNMPTestEntry 8 }

tFilterRSTHoldDown OBJECT-TYPE
    SYNTAX      Unsigned32 (0..86400)
    UNITS        "seconds"
    MAX-ACCESS  read-create
    STATUS      obsolete
    DESCRIPTION
        "The value of tFilterRSTHoldDown specifies the amount of time
        in seconds that the system should be held down if any of the test
        has marked it unreachable.

        This object is obsoleted in release 13.0."
    DEFVAL { 0 }
    ::= { tFilterRedirectSNMPTestEntry 9 }

tFilterRSTHoldDownRemain OBJECT-TYPE
    SYNTAX      Unsigned32 (0..86400)
    UNITS        "seconds"
    MAX-ACCESS  read-only
    STATUS      obsolete
    DESCRIPTION
        "The value of tFilterRSTHoldDownRemain indicates the amount of time
        in seconds that the system will remain in held down state before
        being used again.

        This object is obsoleted in release 13.0."
    ::= { tFilterRedirectSNMPTestEntry 10 }

tFilterRSTLastActionTime OBJECT-TYPE
    SYNTAX      TimeStamp
    MAX-ACCESS  read-only
    STATUS      obsolete
    DESCRIPTION
        "tFilterRSTLastActionTime maintains the time stamp when this test
        received a response for a probe sent out.

        This object is obsoleted in release 13.0."
    ::= { tFilterRedirectSNMPTestEntry 11 }

tFilterRSTLastOID OBJECT-TYPE
    SYNTAX     OBJECT IDENTIFIER
    MAX-ACCESS read-only
    STATUS     obsolete
    DESCRIPTION
     "The object tFilterRSTLastOID holds the OID received in the
     response.

     This object is obsoleted in release 13.0."
    ::= { tFilterRedirectSNMPTestEntry 12 }

tFilterRSTLastType OBJECT-TYPE
    SYNTAX      INTEGER {
                    none(0),
                    counter32(1),
                    unsigned32(2),
                    timeTicks(3),
                    integer32(4),
                    ipAddress(5),
                    octetString(6),
                    objectId(7),
                    counter64(8),
                    opaque(9)
                }
    MAX-ACCESS  read-only
    STATUS      obsolete
    DESCRIPTION
     "tFilterRSTLastType maintains the type of the value received.
      A value of none(0) indicated that no value has been received.

      This object is obsoleted in release 13.0."
    ::= { tFilterRedirectSNMPTestEntry  13 }

tFilterRSTLastCounter32Val OBJECT-TYPE
    SYNTAX      Counter32
    MAX-ACCESS  read-only
    STATUS      obsolete
    DESCRIPTION
     "The value tFilterRSTLastType is 'counter32'.

     This object is obsoleted in release 13.0."
    ::= { tFilterRedirectSNMPTestEntry  14 }

tFilterRSTLastUnsigned32Val OBJECT-TYPE
    SYNTAX      Unsigned32
    MAX-ACCESS  read-only
    STATUS      obsolete
    DESCRIPTION
     "The value tFilterRSTLastType is 'unsigned32'.

     This object is obsoleted in release 13.0."
    ::= { tFilterRedirectSNMPTestEntry  15 }

tFilterRSTLastTimeTicksVal OBJECT-TYPE
    SYNTAX      TimeTicks
    MAX-ACCESS  read-only
    STATUS      obsolete
    DESCRIPTION
     "The value tFilterRSTLastType is 'timeTicks'.

     This object is obsoleted in release 13.0."
    ::= { tFilterRedirectSNMPTestEntry  16 }

tFilterRSTLastInt32Val OBJECT-TYPE
    SYNTAX      Integer32
    MAX-ACCESS  read-only
    STATUS      obsolete
    DESCRIPTION
     "The value tFilterRSTLastType is 'integer32'.

     This object is obsoleted in release 13.0."
    ::= { tFilterRedirectSNMPTestEntry  17 }

tFilterRSTLastOctetStringVal OBJECT-TYPE
    SYNTAX      OCTET STRING
    MAX-ACCESS  read-only
    STATUS      obsolete
    DESCRIPTION
     "The value tFilterRSTLastType is 'octetString'.

     This object is obsoleted in release 13.0."
    ::= { tFilterRedirectSNMPTestEntry  18 }

tFilterRSTLastIpAddressVal OBJECT-TYPE
    SYNTAX      IpAddress
    MAX-ACCESS  read-only
    STATUS      obsolete
    DESCRIPTION
     "The value tFilterRSTLastType is 'ipAddress'. Although
     this seems to be unfriendly for IPv6, we have to
     recognize that there are a number of older MIBs that do
     contain an IPv4 format address, known as IpAddress.

     IPv6 addresses are represented using TAddress or InetAddress,
     and so the underlying datatype is OCTET STRING, and their
     value would be stored in the tFilterRSTLastOctetStringVal
     column.

     This object is obsoleted in release 13.0."
    ::= { tFilterRedirectSNMPTestEntry  19 }

tFilterRSTLastOidVal OBJECT-TYPE
    SYNTAX      OBJECT IDENTIFIER
    MAX-ACCESS  read-only
    STATUS      obsolete
    DESCRIPTION
     "The value tFilterRSTLastType is 'objectId'.

     This object is obsoleted in release 13.0."
    ::= { tFilterRedirectSNMPTestEntry  20 }

tFilterRSTLastCounter64Val OBJECT-TYPE
    SYNTAX      Counter64
    MAX-ACCESS  read-only
    STATUS      obsolete
    DESCRIPTION
     "The value tFilterRSTLastType is 'counter64'.

     This object is obsoleted in release 13.0."
    ::= { tFilterRedirectSNMPTestEntry  21 }

tFilterRSTLastOpaqueVal OBJECT-TYPE
    SYNTAX      Opaque
    MAX-ACCESS  read-only
    STATUS      obsolete
    DESCRIPTION
     "The value tFilterRSTLastType is 'opaque'.

     This object is obsoleted in release 13.0."
    ::= { tFilterRedirectSNMPTestEntry  22 }

tFilterRSTLastAction OBJECT-TYPE
    SYNTAX      INTEGER {
                     enable (1),
                     disable (2),
                     none (3)
                 }
    MAX-ACCESS  read-only
    STATUS      obsolete
    DESCRIPTION
        "tFilterRSTLastAction maintains impact that the last test probe
        made on the operational status of the destination as maintained
        in tFilterRDOperState.

        If the last action was 'disable', the destination may not be
        used for tFilterRSTHoldDown seconds.

        This object is obsoleted in release 13.0."
    ::= { tFilterRedirectSNMPTestEntry 23 }

tFilterRSTLastPrioChange OBJECT-TYPE
    SYNTAX      Integer32 (-255..255)
    MAX-ACCESS  read-only
    STATUS      obsolete
    DESCRIPTION
        "If the last action on the operational state of the destination
        i.e. tFilterRSTLastAction is 'enable', tFilterRSTLastPrioChange
        maintains the impact that the last test probe made on the
        operational priority of the destination.

        In other cases, this object has no significance and hence should
        be holding the value '0'.

        This object is obsoleted in release 13.0."
    ::= { tFilterRedirectSNMPTestEntry 24 }

tFilterRSTNextRespIndex OBJECT-TYPE
    SYNTAX      Integer32 (-1|1..2147483647)
    MAX-ACCESS  read-only
    STATUS      obsolete
    DESCRIPTION
        "The value of tFilterRSTNextRespIndex indicates the next response index
        to be used while creating a row in the tFilterRedirectSNMPRespTable.

        The value of '-1' means that the maximum number of return values
        for this OID are already configured.

        This object is obsoleted in release 13.0."
    ::= { tFilterRedirectSNMPTestEntry 25 }


--
-- Filter Redirect SNMP Response Table
--

tFilterRedirectSNMPRespTable OBJECT-TYPE
    SYNTAX      SEQUENCE OF TFilterRedirectSNMPRespEntry
    MAX-ACCESS  not-accessible
    STATUS      obsolete
    DESCRIPTION
        "Each row in this table holds the effect of the test on the
        destination for a specific return value.

        Each row is created once and cannot be modified after creation.
        Any change attempts will be silently discarded.

        This table is obsoleted in release 13.0 and replaced by
        tFilterRPlcySNMPRespTable."
    ::= { tFilterObjects 13 }

tFilterRedirectSNMPRespEntry OBJECT-TYPE
    SYNTAX      TFilterRedirectSNMPRespEntry
    MAX-ACCESS  not-accessible
    STATUS      obsolete
    DESCRIPTION
        "Information about action to be taken for a specific destination
        when a specific response is received.

        Each row is created once and cannot be modified after creation.
        Any change attempts will be silently discarded.

        This object is obsoleted in release 13.0."
    INDEX {
              tFilterRedirectPolicy,
              tFilterRedirectDest,
              tFilterRedirectSNMPTest,
              tFilterRSTRespId
          }
    ::= { tFilterRedirectSNMPRespTable 1 }

TFilterRedirectSNMPRespEntry ::= SEQUENCE
    {
        tFilterRSTRespId          Integer32,
        tFilterRSTRespRowStatus   RowStatus,
        tFilterRSTRespAction      INTEGER,
        tFilterRSTRespPrioChange  Unsigned32,
        tFilterRSTRespOID         OBJECT IDENTIFIER,
        tFilterRSTRespType        INTEGER,
        tFilterRSTCounter32Val    Counter32,
        tFilterRSTUnsigned32Val   Unsigned32,
        tFilterRSTTimeTicksVal    TimeTicks,
        tFilterRSTInt32Val        Integer32,
        tFilterRSTOctetStringVal  OCTET STRING,
        tFilterRSTIpAddressVal    IpAddress,
        tFilterRSTOidVal          OBJECT IDENTIFIER,
        tFilterRSTCounter64Val    Counter64,
        tFilterRSTOpaqueVal       Opaque
    }

tFilterRSTRespId OBJECT-TYPE
    SYNTAX      Integer32 (1..2147483647)
    MAX-ACCESS  not-accessible
    STATUS      obsolete
    DESCRIPTION
        "tFilterRSTRespId holds the response value received from
        the destination.

        This object is obsoleted in release 13.0."
    ::= { tFilterRedirectSNMPRespEntry 1 }

tFilterRSTRespRowStatus OBJECT-TYPE
    SYNTAX      RowStatus
    MAX-ACCESS  read-create
    STATUS      obsolete
    DESCRIPTION
        "This object allows response strings to be specified for a specific
        test and the change it will cause to the priority of the destination.

        This object is obsoleted in release 13.0."
    ::= { tFilterRedirectSNMPRespEntry 2 }

tFilterRSTRespAction OBJECT-TYPE
    SYNTAX      INTEGER {
                     increase (1),
                     decrease (2),
                     disable (3)
                     }
    MAX-ACCESS  read-create
    STATUS      obsolete
    DESCRIPTION
        "tFilterRSTRespAction specifies the type of change that should
        be made to the destination priority tFilterRDOperPriority, if
        the return value is same as tFilterRSTRespId.
        If tFilterRSTRespPrioChange is 0 this field will be set to 'disable'.

        This field cannot be modified after creation. Any change attempts
        will be silently discarded.

        This object is obsoleted in release 13.0."
    DEFVAL { disable }
    ::= { tFilterRedirectSNMPRespEntry 3 }

tFilterRSTRespPrioChange OBJECT-TYPE
    SYNTAX      Unsigned32 (0..255)
    MAX-ACCESS  read-create
    STATUS      obsolete
    DESCRIPTION
        "tFilterRSTRespPrioChange specifies the amount of change to
        be made to the priority of the destination if the
        tFilterRSTRespAction is either 'increase' or 'decrease'.
        If tFilterRSTRespAction is 'disable', this field will be set to 0.

        This field cannot be modified after creation. Any change attempts
        will be silently discarded.

        This object is obsoleted in release 13.0."
    DEFVAL { 0 }
    ::= { tFilterRedirectSNMPRespEntry 4 }

tFilterRSTRespOID OBJECT-TYPE
    SYNTAX     OBJECT IDENTIFIER
    MAX-ACCESS read-create
    STATUS     obsolete
    DESCRIPTION
        "The object tFilterRSTRespOID holds the OID to be received in the
        response.

        This field cannot be modified after creation. Any change attempts
        will be silently discarded.

        This object is obsoleted in release 13.0."
    ::= { tFilterRedirectSNMPRespEntry 5 }

tFilterRSTRespType OBJECT-TYPE
    SYNTAX      INTEGER {
                    counter32(1),
                    unsigned32(2),
                    timeTicks(3),
                    integer32(4),
                    ipAddress(5),
                    octetString(6),
                    objectId(7),
                    counter64(8),
                    opaque(9)
                }
    MAX-ACCESS  read-create
    STATUS      obsolete
    DESCRIPTION
     "tFilterRSTRespType maintains the type of the value to be received.

      Note: types 'objectId' and 'counter64' are not supported for now,
      and will be rejected when used.

      This field cannot be modified after creation. Any change attempts
      will be silently discarded.

      This object is obsoleted in release 13.0."
    ::= { tFilterRedirectSNMPRespEntry  6 }

tFilterRSTCounter32Val OBJECT-TYPE
    SYNTAX      Counter32
    MAX-ACCESS  read-create
    STATUS      obsolete
    DESCRIPTION
     "The value tFilterRSTRespType is 'counter32'.
      This field cannot be modified after creation. Any change attempts
      will be silently discarded.

      This object is obsoleted in release 13.0."
    ::= { tFilterRedirectSNMPRespEntry  7 }

tFilterRSTUnsigned32Val OBJECT-TYPE
    SYNTAX      Unsigned32
    MAX-ACCESS  read-create
    STATUS      obsolete
    DESCRIPTION
     "The value tFilterRSTRespType is 'unsigned32'.
      This field cannot be modified after creation. Any change attempts
      will be silently discarded.

      This object is obsoleted in release 13.0."
    ::= { tFilterRedirectSNMPRespEntry  8 }

tFilterRSTTimeTicksVal OBJECT-TYPE
    SYNTAX      TimeTicks
    MAX-ACCESS  read-create
    STATUS      obsolete
    DESCRIPTION
     "The value tFilterRSTRespType is 'timeTicks'.
      This field cannot be modified after creation. Any change attempts
      will be silently discarded.

      This object is obsoleted in release 13.0."
    ::= { tFilterRedirectSNMPRespEntry  9 }

tFilterRSTInt32Val OBJECT-TYPE
    SYNTAX      Integer32
    MAX-ACCESS  read-create
    STATUS      obsolete
    DESCRIPTION
     "The value tFilterRSTRespType is 'integer32'.
      This field cannot be modified after creation. Any change attempts
      will be silently discarded.

      This object is obsoleted in release 13.0."
    ::= { tFilterRedirectSNMPRespEntry  10 }

tFilterRSTOctetStringVal OBJECT-TYPE
    SYNTAX      OCTET STRING
    MAX-ACCESS  read-create
    STATUS      obsolete
    DESCRIPTION
     "The value tFilterRSTRespType is 'octetString'.
      This field cannot be modified after creation. Any change attempts
      will be silently discarded.

      This object is obsoleted in release 13.0."
    ::= { tFilterRedirectSNMPRespEntry  11 }

tFilterRSTIpAddressVal OBJECT-TYPE
    SYNTAX      IpAddress
    MAX-ACCESS  read-create
    STATUS      obsolete
    DESCRIPTION
     "The value tFilterRSTRespType is 'ipAddress'. Although
     this seems to be unfriendly for IPv6, we have to
     recognize that there are a number of older MIBs that do
     contain an IPv4 format address, known as IpAddress.

     IPv6 addresses are represented using TAddress or InetAddress,
     and so the underlying datatype is OCTET STRING, and their
     value would be stored in the tFilterRSTOctetStringVal
     column.

     This field cannot be modified after creation. Any change attempts
     will be silently discarded.

     This object is obsoleted in release 13.0."
    ::= { tFilterRedirectSNMPRespEntry  12 }

tFilterRSTOidVal OBJECT-TYPE
    SYNTAX      OBJECT IDENTIFIER
    MAX-ACCESS  read-create
    STATUS      obsolete
    DESCRIPTION
     "The response value if tFilterRSTRespType is set to 'objectId'.
      This field cannot be modified after creation. Any change attempts
      will be silently discarded.

      This object is obsoleted in release 13.0."
    ::= { tFilterRedirectSNMPRespEntry  13 }

tFilterRSTCounter64Val OBJECT-TYPE
    SYNTAX      Counter64
    MAX-ACCESS  read-create
    STATUS      obsolete
    DESCRIPTION
     "The response value if tFilterRSTRespType is set to 'counter64'.
      This field cannot be modified after creation. Any change attempts
      will be silently discarded.

      This object is obsoleted in release 13.0."
    ::= { tFilterRedirectSNMPRespEntry  14 }

tFilterRSTOpaqueVal OBJECT-TYPE
    SYNTAX      Opaque
    MAX-ACCESS  read-create
    STATUS      obsolete
    DESCRIPTION
     "The value tFilterRSTRespType is 'opaque'.
      This field cannot be modified after creation. Any change attempts
      will be silently discarded.

      This object is obsoleted in release 13.0."
    ::= { tFilterRedirectSNMPRespEntry  15 }


--
-- Filter Redirect URL Test Table
--

tFilterRedirectURLTestTable OBJECT-TYPE
    SYNTAX      SEQUENCE OF TFilterRedirectURLTestEntry
    MAX-ACCESS  not-accessible
    STATUS      obsolete
    DESCRIPTION
        "Contains a List of all redirect snmp tests configured on this
        system.

        This table is obsoleted in release 13.0 and replaced by
        tFilterRPlcyURLTestTable."
    ::= { tFilterObjects 14 }

tFilterRedirectURLTestEntry OBJECT-TYPE
    SYNTAX      TFilterRedirectURLTestEntry
    MAX-ACCESS  not-accessible
    STATUS      obsolete
    DESCRIPTION
        "Information about a specific URL test configured for a destination.
        Entries are created/deleted  by user. Entries have a presumed
        StorageType of nonVolatile.

        This object is obsoleted in release 13.0."
    INDEX {
              tFilterRedirectPolicy,
              tFilterRedirectDest,
              tFilterRedirectURLTest
          }
    ::= { tFilterRedirectURLTestTable 1 }

TFilterRedirectURLTestEntry ::= SEQUENCE
    {
        tFilterRedirectURLTest    TNamedItem,
        tFilterRUTRowStatus       RowStatus,
        tFilterRUTURL             DisplayString,
        tFilterRUTHTTPVersion     DisplayString,
        tFilterRUTInterval        Unsigned32,
        tFilterRUTTimeout         Unsigned32,
        tFilterRUTDropCount       Unsigned32,
        tFilterRUTHoldDown        Unsigned32,
        tFilterRUTHoldDownRemain  Unsigned32,
        tFilterRUTLastActionTime  TimeStamp,
        tFilterRUTLastRetCode     Unsigned32,
        tFilterRUTLastAction      INTEGER,
        tFilterRUTLastPrioChange  Integer32
    }

tFilterRedirectURLTest OBJECT-TYPE
    SYNTAX      TNamedItem
    MAX-ACCESS  not-accessible
    STATUS      obsolete
    DESCRIPTION
        "tFilterRedirectURLTest holds the name of the URL test.

        This object is obsoleted in release 13.0."
    ::= { tFilterRedirectURLTestEntry 1 }

tFilterRUTRowStatus OBJECT-TYPE
    SYNTAX      RowStatus
    MAX-ACCESS  read-create
    STATUS      obsolete
    DESCRIPTION
        "tFilterRUTRowStatus allows tests to be created and deleted in the
        tFilterRedirectURLTestTable.

        This object is obsoleted in release 13.0."
    ::= { tFilterRedirectURLTestEntry 2 }

tFilterRUTURL OBJECT-TYPE
    SYNTAX      DisplayString
    MAX-ACCESS  read-create
    STATUS      obsolete
    DESCRIPTION
        "This object holds the URL to be probed.

        This object is obsoleted in release 13.0."
    DEFVAL { ''H }
    ::= { tFilterRedirectURLTestEntry 3 }

tFilterRUTHTTPVersion OBJECT-TYPE
    SYNTAX      DisplayString
    MAX-ACCESS  read-create
    STATUS      obsolete
    DESCRIPTION
        "The HTTP Version to be used while performing the URL test.
        The system by default uses HTTP Version 1.1 until explicitly
        specified.

        This object is obsoleted in release 13.0."
    DEFVAL { ''H }
    ::= { tFilterRedirectURLTestEntry 4 }

tFilterRUTInterval OBJECT-TYPE
    SYNTAX      Unsigned32 (1..60)
    UNITS        "seconds"
    MAX-ACCESS  read-create
    STATUS      obsolete
    DESCRIPTION
        "The value of tFilterRUTInterval specifies the amount of time
        in seconds between consecutive requests sent to the far end
        host.

        This object is obsoleted in release 13.0."
    DEFVAL { 1 }
    ::= { tFilterRedirectURLTestEntry 5 }

tFilterRUTTimeout OBJECT-TYPE
    SYNTAX      Unsigned32 (1..60)
    UNITS        "seconds"
    MAX-ACCESS  read-create
    STATUS      obsolete
    DESCRIPTION
        "The value of tFilterRUTTimeout specifies the amount of time
        in seconds that is allowed for receiving a response from the
        far end host. If a reply is not received within this time the
        far end host is considered unresponsive.

        This object is obsoleted in release 13.0."
    DEFVAL { 1 }
    ::= { tFilterRedirectURLTestEntry 6 }

tFilterRUTDropCount OBJECT-TYPE
    SYNTAX      Unsigned32 (1..60)
    MAX-ACCESS  read-create
    STATUS      obsolete
    DESCRIPTION
        "The value of tFilterRUTDropCount specifies the number of
        consecutive requests that must fail for the destination to
        declared unreachable.

        This object is obsoleted in release 13.0."
    DEFVAL { 3 }
    ::= { tFilterRedirectURLTestEntry 7 }

tFilterRUTHoldDown OBJECT-TYPE
    SYNTAX      Unsigned32 (0..86400)
    UNITS        "seconds"
    MAX-ACCESS  read-create
    STATUS      obsolete
    DESCRIPTION
        "The value of tFilterRUTHoldDown specifies the amount of time
        in seconds that the system should be held down if any of the test
        has marked it unreachable.

        This object is obsoleted in release 13.0."
    DEFVAL { 0 }
    ::= { tFilterRedirectURLTestEntry 8 }

tFilterRUTHoldDownRemain OBJECT-TYPE
    SYNTAX      Unsigned32 (0..86400)
    UNITS        "seconds"
    MAX-ACCESS  read-only
    STATUS      obsolete
    DESCRIPTION
        "The value of tFilterRUTHoldDownRemain indicates the amount of time
        in seconds that the system will remain in held down state before
        being used again.

        This object is obsoleted in release 13.0."
    ::= { tFilterRedirectURLTestEntry 9 }

tFilterRUTLastActionTime OBJECT-TYPE
    SYNTAX      TimeStamp
    MAX-ACCESS  read-only
    STATUS      obsolete
    DESCRIPTION
        "tFilterRUTLastActionTime maintains the time stamp when this test
        received a response for a probe sent out.

        This object is obsoleted in release 13.0."
    ::= { tFilterRedirectURLTestEntry 10 }

tFilterRUTLastRetCode OBJECT-TYPE
    SYNTAX      Unsigned32
    MAX-ACCESS  read-only
    STATUS      obsolete
    DESCRIPTION
        "tFilterRUTLastRetCode holds the return code received in the last
        response.

        This object is obsoleted in release 13.0."
    ::= { tFilterRedirectURLTestEntry 11 }

tFilterRUTLastAction OBJECT-TYPE
    SYNTAX      INTEGER {
                     enable (1),
                     disable (2),
                     none (3)
                 }
    MAX-ACCESS  read-only
    STATUS      obsolete
    DESCRIPTION
        "tFilterRUTLastAction maintains impact that the last test probe
        made on the operational status of the destination as maintained
        in tFilterRDOperState.

        If the last action was 'disable', the destination may not be
        used for tFilterRUTHoldDown seconds.

        This object is obsoleted in release 13.0."
    ::= { tFilterRedirectURLTestEntry 12 }

tFilterRUTLastPrioChange OBJECT-TYPE
    SYNTAX      Integer32 (-255..255)
    MAX-ACCESS  read-only
    STATUS      obsolete
    DESCRIPTION
        "If the last action on the operational state of the destination
        i.e. tFilterRUTLastAction is 'enable', tFilterRUTLastPrioChange
        maintains the impact that the last test probe made on the
        operational priority of the destination.

        In other cases, this object has no significance and hence should
        be holding the value '0'.

        This object is obsoleted in release 13.0."
    ::= { tFilterRedirectURLTestEntry 13 }


--
-- Filter Redirect URL Response Table
--

tFilterRedirectURLRespTable OBJECT-TYPE
    SYNTAX      SEQUENCE OF TFilterRedirectURLRespEntry
    MAX-ACCESS  not-accessible
    STATUS      obsolete
    DESCRIPTION
        "Each row in this table holds the effect of the test on
        the destination for a range of return values.

        This table is obsoleted in release 13.0 and replaced by
        tFilterRPlcyURLRespTable."
    ::= { tFilterObjects 15 }

tFilterRedirectURLRespEntry OBJECT-TYPE
    SYNTAX      TFilterRedirectURLRespEntry
    MAX-ACCESS  not-accessible
    STATUS      obsolete
    DESCRIPTION
        "Information about action to be taken for a specific destination
        when a return value within the range specified between
        tFilterRedirectURLLowRespCode and tFilterRedirectURLHighRespCode
        is received.

        This object is obsoleted in release 13.0."
    INDEX {
              tFilterRedirectPolicy,
              tFilterRedirectDest,
              tFilterRedirectURLTest,
              tFilterRedirectURLLowRespCode,
              tFilterRedirectURLHighRespCode
          }
    ::= { tFilterRedirectURLRespTable 1 }

TFilterRedirectURLRespEntry ::= SEQUENCE
    {
        tFilterRedirectURLLowRespCode  Unsigned32,
        tFilterRedirectURLHighRespCode Unsigned32,
        tFilterRUTRespRowStatus        RowStatus,
        tFilterRUTRespAction           INTEGER,
        tFilterRUTRespPrioChange       Unsigned32
    }

tFilterRedirectURLLowRespCode OBJECT-TYPE
    SYNTAX      Unsigned32
    MAX-ACCESS  not-accessible
    STATUS      obsolete
    DESCRIPTION
        "tFilterRedirectURLLowRespCode specifies the lower return
        code of the range specified by this entry.

        This object is obsoleted in release 13.0."
    ::= { tFilterRedirectURLRespEntry 1 }

tFilterRedirectURLHighRespCode OBJECT-TYPE
    SYNTAX      Unsigned32
    MAX-ACCESS  not-accessible
    STATUS      obsolete
    DESCRIPTION
        "tFilterRedirectURLHighRespCode specifies the higher return
        code of the range specified by this entry.

        This object is obsoleted in release 13.0."
    ::= { tFilterRedirectURLRespEntry 2 }

tFilterRUTRespRowStatus OBJECT-TYPE
    SYNTAX      RowStatus
    MAX-ACCESS  read-create
    STATUS      obsolete
    DESCRIPTION
        "tFilterRUTRespRowStatus allows the mapping of a range of
        return codes returned from a specific test to the change it
        will cause to the priority of the destination.

        This object is obsoleted in release 13.0."
    ::= { tFilterRedirectURLRespEntry 3 }

tFilterRUTRespAction OBJECT-TYPE
    SYNTAX      INTEGER {
                     increase (1),
                     decrease (2),
                     disable  (3)
                     }
    MAX-ACCESS  read-create
    STATUS      obsolete
    DESCRIPTION
        "If the tFilterRUTRespAction is either 'increase(1)' or 'decrease(2)'
        tFilterRUTRespPrioChange specifies the offset to be applied to the
        destination base priority (tFilterRDAdminPriority) in order to
        compute the tFilterRDOperPriority as a result of this test.

        If the tFilterRUTRespAction is set to 'disable(3)', on the reception
        of the specified response, the destination will be deemed
        unusable and the tFilterRDOperPriority will be set to '0'.

        The value of tFilterRUTRespAction will be forced by the system to the
        value 'disable(3)' if the tFilterRUTRespPrioChange has the value '0'.
        Any change attempts will be silently discarded in this case.

        This object is obsoleted in release 13.0."
    DEFVAL { disable }
    ::= { tFilterRedirectURLRespEntry 4 }

tFilterRUTRespPrioChange OBJECT-TYPE
    SYNTAX      Unsigned32 (0..255)
    MAX-ACCESS  read-create
    STATUS      obsolete
    DESCRIPTION
        "tFilterRUTRespPrioChange specifies the amount of change
        to be made to the priority of the destination if the
        tFilterRUTRespAction is either 'increase' or 'decrease'.

        If tFilterRUTRespAction is 'disable', tFilterRUTRespPrioChange will
        be forced to 0. Any change to tFilterRUTRespPrioChange will be
        silently discarded in this case.

        Setting the object tFilterRUTRespPrioChange to 0 will cause the value of
        tFilterRUTRespAction to be set to 'disable'.

        This object is obsoleted in release 13.0."
    DEFVAL { 0 }
    ::= { tFilterRedirectURLRespEntry 5 }

--
-- Filter Redirect Ping Test Table
--

tFilterRedirectPingTestTable OBJECT-TYPE
    SYNTAX      SEQUENCE OF TFilterRedirectPingTestEntry
    MAX-ACCESS  not-accessible
    STATUS      obsolete
    DESCRIPTION
        "Contains a List of all redirect Ping tests configured on this
        system.

        This table is obsoleted in release 13.0 and replaced by
        tFilterRPlcyPingTestTable."
    ::= { tFilterObjects 16 }

tFilterRedirectPingTestEntry OBJECT-TYPE
    SYNTAX      TFilterRedirectPingTestEntry
    MAX-ACCESS  not-accessible
    STATUS      obsolete
    DESCRIPTION
        "Information about a specific Ping test configured for a destination.
        Entries are created/deleted  by user. Entries have a presumed
        StorageType of nonVolatile.

        This object is obsoleted in release 13.0."
    INDEX {
              tFilterRedirectPolicy,
              tFilterRedirectDest
          }
    ::= { tFilterRedirectPingTestTable 1 }

TFilterRedirectPingTestEntry ::= SEQUENCE
    {
        tFilterRPTRowStatus       RowStatus,
        tFilterRPTInterval        Unsigned32,
        tFilterRPTTimeout         Unsigned32,
        tFilterRPTDropCount       Unsigned32,
        tFilterRPTHoldDown        Unsigned32,
        tFilterRPTHoldDownRemain  Unsigned32,
        tFilterRPTLastActionTime  TimeStamp,
        tFilterRPTLastAction      INTEGER
    }

tFilterRPTRowStatus OBJECT-TYPE
    SYNTAX      RowStatus
    MAX-ACCESS  read-create
    STATUS      obsolete
    DESCRIPTION
        "This object allows tests to be created and deleted in the
         tFilterRedirectPingTestTable.

         This object is obsoleted in release 13.0."
    ::= { tFilterRedirectPingTestEntry 1 }

tFilterRPTInterval OBJECT-TYPE
    SYNTAX      Unsigned32 (1..60)
    UNITS        "seconds"
    MAX-ACCESS  read-create
    STATUS      obsolete
    DESCRIPTION
        "The value of tFilterRPTInterval specifies the amount of time
        in seconds between consecutive requests sent to the far end
        host.

        Note that the value of tFilterRPTInterval can only be modified if the
        value of the corresponding tFilterRPAdminState and/or
        tFilterRDAdminState object is outOfService.

        This object is obsoleted in release 13.0."
    DEFVAL { 1 }
    ::= { tFilterRedirectPingTestEntry 2 }

tFilterRPTTimeout OBJECT-TYPE
    SYNTAX      Unsigned32 (1..60)
    UNITS        "seconds"
    MAX-ACCESS  read-create
    STATUS      obsolete
    DESCRIPTION
        "The value of tFilterRPTTimeout specifies the amount of time
        in seconds that is allowed for receiving a response from the
        far end host. If a reply is not received within this time the
        far end host is considered unresponsive.

        Note that the value of tFilterRPTTimeout can only be modified if the
        value of the corresponding tFilterRPAdminState and/or
        tFilterRDAdminState object is outOfService.

        This object is obsoleted in release 13.0."
    DEFVAL { 1 }
    ::= { tFilterRedirectPingTestEntry 3 }

tFilterRPTDropCount OBJECT-TYPE
    SYNTAX      Unsigned32 (1..60)
    MAX-ACCESS  read-create
    STATUS      obsolete
    DESCRIPTION
        "The value of tFilterRPTDropCount specifies the number of
        consecutive requests that must fail for the destination to
        declared unreachable.

        This object is obsoleted in release 13.0."
    DEFVAL { 3 }
    ::= { tFilterRedirectPingTestEntry 4 }

tFilterRPTHoldDown OBJECT-TYPE
    SYNTAX      Unsigned32 (0..86400)
    UNITS        "seconds"
    MAX-ACCESS  read-create
    STATUS      obsolete
    DESCRIPTION
        "The value of tFilterRPTHoldDown specifies the amount of time
        in seconds that the system should be held down if any of the test
        has marked it unreachable.

        This object is obsoleted in release 13.0."
    DEFVAL { 0 }
    ::= { tFilterRedirectPingTestEntry 5 }

tFilterRPTHoldDownRemain OBJECT-TYPE
    SYNTAX      Unsigned32 (0..86400)
    UNITS        "seconds"
    MAX-ACCESS  read-only
    STATUS      obsolete
    DESCRIPTION
        "The value of tFilterRPTHoldDownRemain indicates the amount of time
        in seconds that the system will remain in held down state before
        being used again.

        This object is obsoleted in release 13.0."
    ::= { tFilterRedirectPingTestEntry 6 }

tFilterRPTLastActionTime OBJECT-TYPE
    SYNTAX      TimeStamp
    MAX-ACCESS  read-only
    STATUS      obsolete
    DESCRIPTION
        "tFilterRPTLastActionTime maintains the time stamp when this test
        received a response for a probe sent out.

        This object is obsoleted in release 13.0."
    ::= { tFilterRedirectPingTestEntry 7 }

tFilterRPTLastAction OBJECT-TYPE
    SYNTAX      INTEGER {
                     enable (1),
                     disable (2),
                     none (3)
                 }
    MAX-ACCESS  read-only
    STATUS      obsolete
    DESCRIPTION
        "tFilterRPTLastAction maintains impact that the last test probe
        made on the operational status of the destination as maintained
        in tFilterRDOperState.

        If the last action was 'disable', the destination may not be
        used for tFilterRPTHoldDown seconds.

        This object is obsoleted in release 13.0."
    ::= { tFilterRedirectPingTestEntry 8 }


--
-- Auto IP Filter Entries
--

tAutoIPFilterEntryTable OBJECT-TYPE
    SYNTAX      SEQUENCE OF TAutoIPFilterEntry
    MAX-ACCESS  not-accessible
    STATUS      obsolete
    DESCRIPTION
        "Defines the Nokia SROS series automatic IP filters
         for providing, via SNMP, the capability of gathering
         information regarding the same.

         tAutoIPFilterEntryTable holds a list of all automatic
         filter entries being used for filtering.

         This table is obsoleted in release 3.0."
    ::= { tFilterObjects 17 }

tAutoIPFilterEntry OBJECT-TYPE
    SYNTAX      TAutoIPFilterEntry
    MAX-ACCESS  not-accessible
    STATUS      obsolete
    DESCRIPTION
        "Defines an entry in the tAutoIPFilterEntryTable.

         Entries are created and deleted in this table by the
         system.

         Each entry provides information about a single active
         automatic filter entry.

         This entry is obsoleted in release 3.0."
    INDEX { tAutoIPFilterId, tAutoIPFilterEntrySourceIpAddr }
    ::= { tAutoIPFilterEntryTable 1 }

TAutoIPFilterEntry ::= SEQUENCE
    {
        tAutoIPFilterId                   TFilterID,
        tAutoIPFilterEntrySourceIpAddr    IpAddress,
        tAutoIPFilterEntrySourceIpMask    IpAddressPrefixLength
    }

tAutoIPFilterId OBJECT-TYPE
    SYNTAX      TFilterID (1..65535)
    MAX-ACCESS  not-accessible
    STATUS      obsolete
    DESCRIPTION
        "tAutoIPFilterId serves as a primary index and uniquely
         identifies an application point such as a routed
         interface or a SAP.

         This object is obsoleted in release 3.0."
    ::= { tAutoIPFilterEntry 1 }

tAutoIPFilterEntrySourceIpAddr OBJECT-TYPE
    SYNTAX      IpAddress
    MAX-ACCESS  not-accessible
    STATUS      obsolete
    DESCRIPTION
        "tAutoIPFilterEntrySourceIpAddr specifies the source
         ip-address and also serves as the secondary index to
         this table.

         This object is obsoleted in release 3.0."
    ::= { tAutoIPFilterEntry 2 }

tAutoIPFilterEntrySourceIpMask OBJECT-TYPE
    SYNTAX      IpAddressPrefixLength
    MAX-ACCESS  read-only
    STATUS      obsolete
    DESCRIPTION
        "The value of tAutoIPFilterEntrySourceIpMask indicates the number
         of bits to be matched in the source ip-address.

         This object is obsoleted in release 3.0."
    ::= { tAutoIPFilterEntry 3 }

--
-- Filter Domain Time Stamp
--

tFilterDomainLastChanged OBJECT-TYPE
    SYNTAX      TimeStamp
    MAX-ACCESS  read-only
    STATUS      current
    DESCRIPTION
        "timestamp of last change to tFilterObjects."
    ::= { tFilterTimeStampObjects 1 }

--
-- IPv6 Filter Table
--

tIPv6FilterTable OBJECT-TYPE
    SYNTAX      SEQUENCE OF TIPv6FilterEntry
    MAX-ACCESS  not-accessible
    STATUS      current
    DESCRIPTION
        "Contains a List of all IPv6 filters configured on this system."
    ::= { tFilterObjects 18 }

tIPv6FilterEntry OBJECT-TYPE
    SYNTAX      TIPv6FilterEntry
    MAX-ACCESS  not-accessible
    STATUS      current
    DESCRIPTION
        "Information about a particular IPv6 Filter entry. Entries are
         created/deleted  by user. Entries have a presumed StorageType of
         nonVolatile."
    INDEX { tIPv6FilterId }
    ::= { tIPv6FilterTable 1 }

TIPv6FilterEntry ::= SEQUENCE
    {
        tIPv6FilterId                    TAnyFilterID,
        tIPv6FilterRowStatus             RowStatus,
        tIPv6FilterScope                 TFilterScope,
        tIPv6FilterDescription           TItemDescription,
        tIPv6FilterDefaultAction         TFilterAction,
        tIPv6FilterRadiusInsertPt        TEntryIdOrZero,
        tIPv6FilterRadiusInsertSize      TEntryIdOrZero,
        tIPv6FilterCreditCntrlInsertPt   TEntryIdOrZero,
        tIPv6FilterCreditCntrlInsertSize TEntryIdOrZero,
        tIPv6FilterSubInsertHighWmark    Integer32,
        tIPv6FilterSubInsertLowWmark     Integer32,
        tIpv6FilterCreditCntrlNbrInsertd Unsigned32,
        tIpv6FilterRadiusNbrInsertd      Unsigned32,
        tIpv6FilterName                  TLNamedItemOrEmpty,
        tIPv6FilterHostSharedInsertPt    TEntryIdOrZero,
        tIPv6FilterHostSharedInsertSize  TEntryIdOrZero,
        tIpv6FilterHostSharedNbrInsertd  Unsigned32,
        tIPv6FilterHostSharedHighWmark   Integer32,
        tIPv6FilterHostSharedLowWmark    Integer32,
        tIPv6FilterNbrHostSharedFltrs    Unsigned32,
        tIPv6FilterSharedPccRuleInsrtPt  TEntryIdOrZero,
        tIPv6FilterSharedPccRuleInsrtSiz TEntryIdOrZero,
        tIPv6FilterSharedPccRuleNbrInsrt Unsigned32,
        tIPv6FilterChainToSystemFilter   TruthValue
    }

tIPv6FilterId OBJECT-TYPE
    SYNTAX      TAnyFilterID
    MAX-ACCESS  not-accessible
    STATUS      current
    DESCRIPTION
        "The value of the object tIPv6FilterId uniquely identifies an ip filter.
         User-configured filters have values between (1..65535).
         Other values are reserved for filters that are created (auto-generated)
         by the system.
         Refer to the description of the textual convention TAnyFilterID
         for more details."
    ::= { tIPv6FilterEntry 1 }

tIPv6FilterRowStatus OBJECT-TYPE
    SYNTAX      RowStatus
    MAX-ACCESS  read-create
    STATUS      current
    DESCRIPTION
        "The value of the object tIPv6FilterRowStatus specifies
         the status of the IPv6 filter. The object allows
         entries to be created and deleted in the tIPv6FilterTable."
    ::= { tIPv6FilterEntry 2 }

tIPv6FilterScope OBJECT-TYPE
    SYNTAX      TFilterScope
    MAX-ACCESS  read-create
    STATUS      current
    DESCRIPTION
        "The value of the object tIPv6FilterScope specifies the
         scope of this filter definition."
    DEFVAL { template }
    ::= { tIPv6FilterEntry 3 }

tIPv6FilterDescription OBJECT-TYPE
    SYNTAX      TItemDescription
    MAX-ACCESS  read-create
    STATUS      current
    DESCRIPTION
        "The value of the object tIPv6FilterDescription specifies
         a user-provided description for this filter."
    DEFVAL { ''H }
    ::= { tIPv6FilterEntry 4 }

tIPv6FilterDefaultAction OBJECT-TYPE
    SYNTAX      TFilterAction
    MAX-ACCESS  read-create
    STATUS      current
    DESCRIPTION
        "The value of the object tIPv6FilterDefaultAction specifies
         the action to be taken for packets that do not match any
         of the filter entries.
         The only allowed values for this field are drop(1) and forward(2)."
    DEFVAL { drop }
    ::= { tIPv6FilterEntry 5 }

tIPv6FilterRadiusInsertPt OBJECT-TYPE
    SYNTAX      TEntryIdOrZero
    MAX-ACCESS  read-create
    STATUS      current
    DESCRIPTION
        "The value of tIPv6FilterRadiusInsertPt specifies at what place the
         host specific filter entries received from Radius will be inserted
         in the filter.
        
         The area defined here will be dedicated to those entries, no other
         entries will be allowed.
        
         The value 0 means that no Radius provided host specific filter
         entries can be inserted in the filter.
        
         If tIPv6FilterRadiusInsertSize is set to 0, then this object
         will be put to 0 as well. Any change attempts will be
         silently discarded in this case."
    DEFVAL { 0 }
    ::= { tIPv6FilterEntry 6 }

tIPv6FilterRadiusInsertSize OBJECT-TYPE
    SYNTAX      TEntryIdOrZero
    MAX-ACCESS  read-create
    STATUS      current
    DESCRIPTION
        "The value of tIPv6FilterRadiusInsertSize specifies how many
         host specific filter entries received from Radius for subscriber
         hosts can be inserted in the filter.
        
         If tIPv6FilterRadiusInsertPt is set to 0, then this object
         will be put to 0 as well. Any change attempts will be
         silently discarded in this case."
    DEFVAL { 0 }
    ::= { tIPv6FilterEntry 7 }

tIPv6FilterCreditCntrlInsertPt OBJECT-TYPE
    SYNTAX      TEntryIdOrZero
    MAX-ACCESS  read-create
    STATUS      current
    DESCRIPTION
        "The value of tIPv6FilterCreditCntrlInsertPt specifies at what place
         the filter entries received from Credit Control for a
         particular subscriber host will be inserted in the filter.

         The area defined here will be dedicated to those entries, no other
         entries will be allowed.

         The value 0 means that no Credit Control provided filter entries
         can be inserted in the filter.

         If tIPv6FilterCreditCntrlInsertSize is set to 0, then this object
         will be put to 0 as well. Any change attempts will be
         silently discarded in this case."
    DEFVAL { 0 }
    ::= { tIPv6FilterEntry 8 }

tIPv6FilterCreditCntrlInsertSize OBJECT-TYPE
    SYNTAX      TEntryIdOrZero
    MAX-ACCESS  read-create
    STATUS      current
    DESCRIPTION
        "The value of tIPv6FilterCreditCntrlInsertSize specifies how many
         filter entries received from Credit Control can be inserted in the
         filter.

         If tIPv6FilterCreditCntrlInsertPt is set to 0, then this object
         will be put to 0 as well. Any change attempts will be
         silently discarded in this case."
    DEFVAL { 0 }
    ::= { tIPv6FilterEntry 9 }

tIPv6FilterSubInsertHighWmark OBJECT-TYPE
    SYNTAX      Integer32 (0..100)
    MAX-ACCESS  read-create
    STATUS      current
    DESCRIPTION
        "The value of the object tIPv6FilterSubInsertHighWmark
         specifies the utilization of the filter ranges for filter
         entry insertion, at which a table full alarm will be raised
         by the agent.
         The value 0 indicates that no alarm will be generated."
    DEFVAL { 95 }
    ::= { tIPv6FilterEntry 10 }

tIPv6FilterSubInsertLowWmark OBJECT-TYPE
    SYNTAX      Integer32 (0..100)
    MAX-ACCESS  read-create
    STATUS      current
    DESCRIPTION
        "The value of the object tIPv6FilterSubInsertLowWmark
         specifies the utilization of the filter ranges for filter
         entry insertion, at which a table full alarm will be cleared
         by the agent."
    DEFVAL { 90 }
    ::= { tIPv6FilterEntry 11 }

tIpv6FilterCreditCntrlNbrInsertd OBJECT-TYPE
    SYNTAX      Unsigned32
    MAX-ACCESS  read-only
    STATUS      current
    DESCRIPTION
        "The value of the object tIpv6FilterCreditCntrlNbrInsertd
         indicates how many filter entries are currently inserted
         in the filter on request of credit control."
    ::= { tIPv6FilterEntry 12 }

tIpv6FilterRadiusNbrInsertd OBJECT-TYPE
    SYNTAX      Unsigned32
    MAX-ACCESS  read-only
    STATUS      current
    DESCRIPTION
        "The value of the object tIpv6FilterRadiusNbrInsertd
         indicates how many host specific filter entries are
         currently inserted in the filter on request of RADIUS."
    ::= { tIPv6FilterEntry 13 }

tIpv6FilterName OBJECT-TYPE
    SYNTAX      TLNamedItemOrEmpty
    MAX-ACCESS  read-create
    STATUS      current
    DESCRIPTION
        "The value of tIpv6FilterName specifies the name to associate
        with this filter."
    DEFVAL { ''H }
    ::= { tIPv6FilterEntry 14 }

tIPv6FilterHostSharedInsertPt OBJECT-TYPE
SYNTAX      TEntryIdOrZero
MAX-ACCESS  read-create
STATUS      current
DESCRIPTION
    "The value of tIPv6FilterHostSharedInsertPt specifies at what place the
     filter entries received from Radius that are shared between several
     hosts (host common rules) will be inserted in the filter.

     The area defined here will be dedicated to those entries, no other
     entries will be allowed.

     The value 0 means that no Radius provided host common filter entries
     can be inserted in the filter.

     If tIPv6FilterHostSharedInsertSize is set to 0, then this object
     will be put to 0 as well. Any change attempts will be
     silently discarded in this case."
DEFVAL { 0 }
::= { tIPv6FilterEntry 15 }

tIPv6FilterHostSharedInsertSize OBJECT-TYPE
SYNTAX      TEntryIdOrZero
MAX-ACCESS  read-create
STATUS      current
DESCRIPTION
    "The value of tIPv6FilterHostSharedInsertSize specifies how many
     host common filter entries received from Radius for subscriber hosts
     can be inserted in the filter.

     If tIPv6FilterHostSharedInsertPt is set to 0, then this object
     will be put to 0 as well. Any change attempts will be
     silently discarded in this case."
DEFVAL { 0 }
::= { tIPv6FilterEntry 16 }

tIpv6FilterHostSharedNbrInsertd OBJECT-TYPE
    SYNTAX      Unsigned32
    MAX-ACCESS  read-only
    STATUS      current
    DESCRIPTION
        "The value of the object tIpv6FilterHostSharedNbrInsertd
         indicates how many host common filter entries are currently
         inserted in the filter on request of Radius."
    ::= { tIPv6FilterEntry 17 }

tIPv6FilterHostSharedHighWmark OBJECT-TYPE
    SYNTAX      Integer32 (-1 | 1..8000)
    MAX-ACCESS  read-create
    STATUS      current
    DESCRIPTION
        "The value of the object tIPv6FilterHostSharedHighWmark
         specifies the number of Radius Shared Filters that can be 
         dynamically created in the system before an high watermark
         notification is generated by the system.
         The value -1 specifies that no notifications are sent.
         If any of the watermarks (high or low) is set to -1, both
         watermarks will be set to -1 by the system."
    DEFVAL { -1 }
    ::= { tIPv6FilterEntry 18 }

tIPv6FilterHostSharedLowWmark OBJECT-TYPE
    SYNTAX      Integer32  (-1 | 0..8000)
    MAX-ACCESS  read-create
    STATUS      current
    DESCRIPTION
        "The value of the object tIPv6FilterHostSharedLowWmark
         specifies the number of Radius Shared Filters that are still
         dynamically created in the system before an high watermark
         notification is cleared by the system.
         The value -1 specifies that no notifications are sent.
         If any of the watermarks (high or low) is set to -1, both
         watermarks will be set to -1 by the system."
    DEFVAL { -1 }
    ::= { tIPv6FilterEntry 19 }

tIPv6FilterNbrHostSharedFltrs OBJECT-TYPE
    SYNTAX      Unsigned32
    MAX-ACCESS  read-only
    STATUS      current
    DESCRIPTION
        "The value of the object tIPv6FilterNbrHostSharedFltrs indicates how
         many filters are currently created by Radius or Diameter based on this
         filter. (Both host shared or flow-rule filters.)"
    ::= { tIPv6FilterEntry 20 }

tIPv6FilterSharedPccRuleInsrtPt OBJECT-TYPE
    SYNTAX      TEntryIdOrZero
    MAX-ACCESS  read-create
    STATUS      current
    DESCRIPTION
        "The value of tIPv6FilterSharedPccRuleInsrtPt specifies at what place
         the flow-rule filter entries that are received from Diameter and that
         are shared across several hosts will be inserted in the filter.

         The range defined here will be reserved for those entries; no other
         entries will be allowed in this range.

         The value 0 means that no flow-rule filter entries can be inserted in
         the filter by Diameter.

         If tIPv6FilterSharedPccRuleInsrtSiz is set to 0 then
         tIPv6FilterSharedPccRuleInsrtPt is also set to 0 by the system.

         Note that the range reserved for shared flow-rule entries must not
         overlap with that of either
         tIPv6FilterRadiusInsertPt/tIPv6FilterRadiusInsertSize,
         tIPv6FilterCreditCntrlInsertPt/tIPv6FilterCreditCntrlInsertSize, or
         tIPv6FilterHostSharedInsertPt/tIPv6FilterHostSharedInsertSize"
    DEFVAL { 0 }
    ::= { tIPv6FilterEntry 21 }

tIPv6FilterSharedPccRuleInsrtSiz OBJECT-TYPE
    SYNTAX      TEntryIdOrZero
    MAX-ACCESS  read-create
    STATUS      current
    DESCRIPTION
        "The value of tIPv6FilterSharedPccRuleInsrtSiz specifies how many
         flow-rule filter entries that are received from Diameter and that are
         shared across several hosts can be inserted in the filter.

         The range defined here will be reserved for those entries; no other
         entries will be allowed in this range.

         The value 0 means that no flow-rule filter entries can be inserted in
         the filter by Diameter.

         If tIPv6FilterSharedPccRuleInsrtPt is set to 0 then
         tIPv6FilterSharedPccRuleInsrtSiz is also set to 0 by the system.

         Note that the range reserved for shared flow-rule entries must not
         overlap with that of either
         tIPv6FilterRadiusInsertPt/tIPv6FilterRadiusInsertSize,
         tIPv6FilterCreditCntrlInsertPt/tIPv6FilterCreditCntrlInsertSize, or
         tIPv6FilterHostSharedInsertPt/tIPv6FilterHostSharedInsertSize"
    DEFVAL { 0 }
    ::= { tIPv6FilterEntry 22 }

tIPv6FilterSharedPccRuleNbrInsrt OBJECT-TYPE
    SYNTAX      Unsigned32
    MAX-ACCESS  read-only
    STATUS      current
    DESCRIPTION
        "The value of the object tIPv6FilterSharedPccRuleNbrInsrt indicates how
         many flow-rule filter entries received from Diameter have been inserted
         in this filter"
    ::= { tIPv6FilterEntry 23 }

tIPv6FilterChainToSystemFilter OBJECT-TYPE
    SYNTAX      TruthValue
    MAX-ACCESS  read-create
    STATUS      current
    DESCRIPTION
        "The value of the object tIPv6FilterChainToSystemFilter specifies
         whether this filter policy is chained to the active IPv6 system
         filter policy.

         The active IPv6 system filter policy is defined as a row in
         tFilterSystemFilterTable that have the value of the object
         tFilterSystemFilterType set to 'fltrtypeselIpv6(4)'.

         The value 'true(1)' means this filter policy is chained to
         the active IPv6 system filter policy. The system filter policy's rules
         are executed first before any rules of this filter policy are
         executed.

         The value of this object can be set to 'true(1)' only when the scope
         of this policy (value of the object tIPv6FilterScope) is
         'exclusive(1)' or 'template(2)'.

         The value 'false(2)' means this filter policy is not chained to
         the system filter policy."
    DEFVAL { false }
    ::= { tIPv6FilterEntry 24 }

--
-- IPv6 Filter Entry parameters
--

tIPv6FilterParamsTable OBJECT-TYPE
    SYNTAX      SEQUENCE OF TIPv6FilterParamsEntry
    MAX-ACCESS  not-accessible
    STATUS      current
    DESCRIPTION  "A table of all IPv6 filter match entries for all IPv6 filters"
    ::= { tFilterObjects 19 }

tIPv6FilterParamsEntry OBJECT-TYPE
    SYNTAX      TIPv6FilterParamsEntry
    MAX-ACCESS  not-accessible
    STATUS      current
    DESCRIPTION
        "Information about a particular IPv6 Filter entry.
         Every IPv6 Filter can have zero or more IPv6 Filter match entries.

         A filter entry with no match criteria set will match every
         packet, and the entry action will be taken.

         Entries are created/deleted by user.

         Additional match criteria can be found in tIPv6FilterParamsExtTable.
         
         There is no StorageType object, entries have a presumed
         StorageType of nonVolatile."
    INDEX { tIPv6FilterId, tIPv6FilterParamsIndex }
    ::= { tIPv6FilterParamsTable 1 }

TIPv6FilterParamsEntry ::= SEQUENCE
    {
        tIPv6FilterParamsIndex               TAnyEntryId,
        tIPv6FilterParamsRowStatus           RowStatus,
        tIPv6FilterParamsLogId               TFilterLogId,
        tIPv6FilterParamsDescription         TItemDescription,
        tIPv6FilterParamsAction              TFilterActionOrDefault,
        tIPv6FilterParamsForwardNH           InetAddressIPv6,
        tIPv6FilterParamsForwardNHIndirect   TruthValue,
        tIPv6FilterParamsRemarkDSCP          TDSCPFilterActionValue,
        tIPv6FilterParamsRemarkDSCPMask      TDSCPFilterActionValue,
        tIPv6FilterParamsRemarkDot1p         Dot1PPriority,
        tIPv6FilterParamsSourceIpAddr        InetAddressIPv6,
        tIPv6FilterParamsSourceIpMask        InetAddressPrefixLength,
        tIPv6FilterParamsDestinationIpAddr   InetAddressIPv6,
        tIPv6FilterParamsDestinationIpMask   InetAddressPrefixLength,
        tIPv6FilterParamsNextHeader          TIpProtocol,
        tIPv6FilterParamsSourcePortValue1    TTcpUdpPort,
        tIPv6FilterParamsSourcePortValue2    TTcpUdpPort,
        tIPv6FilterParamsSourcePortOperator  TOperator,
        tIPv6FilterParamsDestPortValue1      TTcpUdpPort,
        tIPv6FilterParamsDestPortValue2      TTcpUdpPort,
        tIPv6FilterParamsDestPortOperator    TOperator,
        tIPv6FilterParamsDSCP                TDSCPNameOrEmpty,
        tIPv6FilterParamsTcpSyn              TItemMatch,
        tIPv6FilterParamsTcpAck              TItemMatch,
        tIPv6FilterParamsIcmpCode            INTEGER,
        tIPv6FilterParamsIcmpType            INTEGER,
        tIPv6FilterParamsCflowdSample        TruthValue,
        tIPv6FilterParamsCflowdIfSample      TruthValue,
        tIPv6FilterParamsForwardNHInterface  DisplayString,
        tIPv6FilterParamsIngressHitCount     Counter64,
        tIPv6FilterParamsEgressHitCount      Counter64,
        tIPv6FilterParamsLogInstantiated     TruthValue,
        tIPv6FilterParamsForwardRedPlcy      TNamedItemOrEmpty,
        tIPv6FilterParamsActiveDest          InetAddressIPv6,
        tIPv6FilterParamsTimeRangeName       TNamedItemOrEmpty,
        tIPv6FilterParamsTimeRangeState      TTimeRangeState,
        tIPv6FilterParamsIngrHitByteCount    Counter64,
        tIPv6FilterParamsEgrHitByteCount     Counter64,
        tIPv6FilterParamsFwdSvcId            TmnxServId,
        tIPv6FilterParamsFwdSapPortId        TmnxPortID,
        tIPv6FilterParamsFwdSapEncapVal      TmnxEncapVal,
        tIPv6FilterParamsFwdSdpBind          SdpBindId,
        tIPv6FilterParamsRedirectURL         TmnxHttpRedirectUrl,
        tIPv6FilterParamsSrcIpPrefixList     TNamedItemOrEmpty,
        tIPv6FilterParamsDstIpPrefixList     TNamedItemOrEmpty,
        tIPv6FilterParamsFragment            INTEGER,
        tIPv6FilterParamsHopByHopOpt         TItemMatch,
        tIPv6FilterParamsRoutingType0        TItemMatch,
        tIPv6FilterParamsPortSelector        TFltrPortSelector,
        tIPv6FilterParamsSrcPortList         TNamedItemOrEmpty,
        tIPv6FilterParamsDstPortList         TNamedItemOrEmpty,
        tIPv6FilterParamsRdirAllwRadOvrd     TruthValue,
        tIPv6FilterParamsFwdRtrId            TmnxVRtrIDOrZero,
        tIPv6FilterParamsSrcIpFullMask       InetAddressIPv6,
        tIPv6FilterParamsDstIpFullMask       InetAddressIPv6,
        tIPv6FilterParamsNatPolicyName       TNamedItemOrEmpty,
        tIPv6FilterParamsFlowLabel           IPv6FlowLabel,
        tIPv6FilterParamsFlowLabelMask       IPv6FlowLabelMask,
        tIPv6FilterParamsFwdLsp              TmnxVRtrMplsLspID,
        tIPv6FilterParamsFwdLspRtrId         TmnxVRtrIDOrZero
    }

tIPv6FilterParamsIndex OBJECT-TYPE
    SYNTAX      TAnyEntryId
    MAX-ACCESS  not-accessible
    STATUS      current
    DESCRIPTION
        "This is the secondary index for the entry. Every IPv6 filter can have
         multiple entries, therefore every IPv6 filter entry is identified by
         the tIPv6FilterId and tIPv6FilterParamsIndex.
         
         Refer to the description of the textual convention TAnyEntryId for more
         info on the allowed values for this object."
    ::= { tIPv6FilterParamsEntry 1 }

tIPv6FilterParamsRowStatus OBJECT-TYPE
    SYNTAX      RowStatus
    MAX-ACCESS  read-create
    STATUS      current
    DESCRIPTION
        "This object allows entries to be created and deleted in the
         tIPv6FilterParamsTable."
    ::= { tIPv6FilterParamsEntry 2 }

tIPv6FilterParamsLogId OBJECT-TYPE
    SYNTAX      TFilterLogId
    MAX-ACCESS  read-create
    STATUS      current
    DESCRIPTION
        "This object specifies the log to use for packets that match
         this entry. The value zero indicates that logging is disabled."
    DEFVAL { 0 }
    ::= { tIPv6FilterParamsEntry 3 }

tIPv6FilterParamsDescription OBJECT-TYPE
    SYNTAX      TItemDescription
    MAX-ACCESS  read-create
    STATUS      current
    DESCRIPTION
        "User-provided description for this filter entry."
    DEFVAL { ''H }
    ::= { tIPv6FilterParamsEntry 4 }

tIPv6FilterParamsAction OBJECT-TYPE
    SYNTAX      TFilterActionOrDefault
    MAX-ACCESS  read-create
    STATUS      current
    DESCRIPTION
        "The action to take for packets that match this filter entry. The value
         default(3) specifies this entry to inherit the behavior defined as the
         default for the filter.

         Setting the values 'forwardEsiL2' and 'forwardEsiL3' explicitly is
         ignored by the system. The values 'forwardEsiL2'(8) and
         'forwardEsiL3'(9) can be set only implicitly by specifying non default
         values of objects specifying parameters for these actions. In such case
         the value of tIPFilterParamsAction will be set to 'forwardEsiL2'(8) or
         'forwardEsiL3'(9) automatically by system.

         The object tIPv6FilterParamsAction supports only subset of filter
         actions. The object tIPvXFltrEntryActAction supports all actions.
         It's recommended to use tIPvXFltrEntryActAction instead of
         tIPv6FilterParamsAction.

         The following value(s) is(are) not supported:
         - reassemble
        "
    DEFVAL { drop }
    ::= { tIPv6FilterParamsEntry 5 }

tIPv6FilterParamsForwardNH OBJECT-TYPE
    SYNTAX      InetAddressIPv6
    MAX-ACCESS  read-create
    STATUS      current
    DESCRIPTION
        "The ipv6-address of the nexthop to which the packet should be forwarded
         if it hits this filter entry. The action of this entry should be
         'forward' in such a case.

         Note that the value of tIPv6FilterParamsForwardNH is silently cleared
         by the system if tIPv6FilterParamsAction is set to value other than
         'forward'(2), or any object related to 'forward' other than
         tIPv6FilterParamsForwardNH or tIPv6FilterParamsForwardNHIndirect
         or tIPv6FilterParamsFwdRtrId is set."
    DEFVAL { '00000000000000000000000000000000'H }
    ::= { tIPv6FilterParamsEntry 6 }

tIPv6FilterParamsForwardNHIndirect OBJECT-TYPE
    SYNTAX      TruthValue
    MAX-ACCESS  read-create
    STATUS      current
    DESCRIPTION
        "tIPv6FilterParamsForwardNHIndirect specifies if the nexthop is
         directly or indirectly reachable.

         Note that the value of tIPv6FilterParamsForwardNHIndirect is silently
         cleared by the system if tIPv6FilterParamsAction is set to value other
         than 'forward'(2), or any object related to 'forward' other than
         tIPv6FilterParamsForwardNH, tIPv6FilterParamsForwardNHIndirect
         or tIPv6FilterParamsFwdRtrId is set."
    DEFVAL { false }
    ::= { tIPv6FilterParamsEntry 7 }

tIPv6FilterParamsRemarkDSCP OBJECT-TYPE
    SYNTAX      TDSCPFilterActionValue
    MAX-ACCESS  read-create
    STATUS      obsolete
    DESCRIPTION
        "The DSCP value that should be remarked in case a packet hits this
         filter entry."
    DEFVAL { -1 }
    ::= { tIPv6FilterParamsEntry 8 }

tIPv6FilterParamsRemarkDSCPMask OBJECT-TYPE
    SYNTAX      TDSCPFilterActionValue
    MAX-ACCESS  read-create
    STATUS      obsolete
    DESCRIPTION
        "tIPv6FilterParamsRemarkDSCPMask specifies the care bits while remarking
         with the DSCP value."
    DEFVAL { 255 }
    ::= { tIPv6FilterParamsEntry 9 }

tIPv6FilterParamsRemarkDot1p OBJECT-TYPE
    SYNTAX      Dot1PPriority
    MAX-ACCESS  read-create
    STATUS      obsolete
    DESCRIPTION
        "tIPv6FilterParamsRemarkDot1p specifies the Dot1p value that needs to be
         remarked on the packet if it hits this filter entry."
    DEFVAL { -1 }
    ::= { tIPv6FilterParamsEntry 10 }

tIPv6FilterParamsSourceIpAddr OBJECT-TYPE
    SYNTAX      InetAddressIPv6
    MAX-ACCESS  read-create
    STATUS      current
    DESCRIPTION
        "IPv6 address to match the source-ip of the packet."
    DEFVAL { '00000000000000000000000000000000'H }
    ::= { tIPv6FilterParamsEntry 11 }

tIPv6FilterParamsSourceIpMask OBJECT-TYPE
    SYNTAX      InetAddressPrefixLength (0..128)
    MAX-ACCESS  read-create
    STATUS      current
    DESCRIPTION
        "If different from 0, the object tIPv6FilterParamsSourceIpMask
         specifies the IPv6 prefix length value for this policy IPv6 Filter
         entry.
         The mask generated from the prefix length value is ANDed with
         the received source IPv6 address to match
         the tIPv6FilterParamsSourceIpAddr.

         If the value of tIPv6FilterParamsSourceIpMask is 0,
         and the value of tIPv6FilterParamsSrcIpFullMask is non zero
         then the value of tIPv6FilterParamsSrcIpFullMask is used as a mask.

         If the value of tIPv6FilterParamsSourceIpMask is non zero,
         it will be equal to the mask expressed in the object
         tIPv6FilterParamsSrcIpFullMask.

         If both tIPv6FilterParamsSourceIpMask and
         tIPv6FilterParamsSrcIpFullMask are set to 0, no matching is done
         on the source IPv6 address.

         If a value is specified for this object, then the value of the
         object tIPv6FilterParamsSrcIpFullMask will be set to reflect
         this same mask."
    DEFVAL { 0 }
    ::= { tIPv6FilterParamsEntry 12 }

tIPv6FilterParamsDestinationIpAddr OBJECT-TYPE
    SYNTAX      InetAddressIPv6
    MAX-ACCESS  read-create
    STATUS      current
    DESCRIPTION
        "IPv6 address to match the destination-ip of the packet."
    DEFVAL { '00000000000000000000000000000000'H }
    ::= { tIPv6FilterParamsEntry 13 }

tIPv6FilterParamsDestinationIpMask OBJECT-TYPE
    SYNTAX      InetAddressPrefixLength (0..128)
    MAX-ACCESS  read-create
    STATUS      current
    DESCRIPTION
        "If different from 0, the object tIPv6FilterParamsDestinationIpMask
         specifies the IPv6 prefix length value for this policy IPv6 Filter
         entry.
         The mask generated from the prefix length value is ANDed with
         the received destination IPv6 address to match
         the tIPv6FilterParamsDestinationIpAddr.

         If the value of tIPv6FilterParamsDestinationIpMask is 0,
         and the value of tIPv6FilterParamsDstIpFullMask is non zero
         then the value of tIPv6FilterParamsDstIpFullMask is used as a mask.

         If the value of tIPv6FilterParamsDestinationIpMask is non zero,
         it will be equal to the mask expressed in the object
         tIPv6FilterParamsDstIpFullMask.

         If both tIPv6FilterParamsDestinationIpMask and
         tIPv6FilterParamsDstIpFullMask are set to 0, no matching is done
         on the destination IPv6 address.

         If a value is specified for this object, then the value of the
         object tIPv6FilterParamsDstIpFullMask will be set to reflect
         this same mask."
    DEFVAL { 0 }
    ::= { tIPv6FilterParamsEntry 14 }

tIPv6FilterParamsNextHeader OBJECT-TYPE
    SYNTAX      TIpProtocol
    MAX-ACCESS  read-create
    STATUS      current
    DESCRIPTION
        "IPv6 next header to match. Set to -1 to disable matching IPv6 next
         header. If the next header is changed the next header specific
         parameters are reset. For instance if next header is changed from TCP
         to UDP, then the objects tIPv6FilterParamsTcpSyn and
         tIPv6FilterParamsTcpAck will be turned off.
         Because the match criteria only pertains to the last next-header, the
         following values are not accepted: 0, 43, 44, 50, 51, and 60."
    DEFVAL { -1 }
    ::= { tIPv6FilterParamsEntry 15 }

tIPv6FilterParamsSourcePortValue1 OBJECT-TYPE
    SYNTAX      TTcpUdpPort
    MAX-ACCESS  read-create
    STATUS      current
    DESCRIPTION
        "TCP/UDP port value1. The value of this object is used as per the
         description for tIPv6FilterParamsSourcePortOperator."
    DEFVAL { 0 }
    ::= { tIPv6FilterParamsEntry 16 }

tIPv6FilterParamsSourcePortValue2 OBJECT-TYPE
    SYNTAX      TTcpUdpPort
    MAX-ACCESS  read-create
    STATUS      current
    DESCRIPTION
        "TCP/UDP port value2. The value of this object is used as per the
         description for tIPv6FilterParamsSourcePortOperator."
    DEFVAL { 0 }
    ::= { tIPv6FilterParamsEntry 17 }

tIPv6FilterParamsSourcePortOperator OBJECT-TYPE
    SYNTAX      TOperator
    MAX-ACCESS  read-create
    STATUS      current
    DESCRIPTION
        "The operator specifies the manner in which
         tIPFilterParamsSourcePortValue1 and tIPFilterParamsSourcePortValue2
         are to be used."
    DEFVAL { none }
    ::= { tIPv6FilterParamsEntry 18 }

tIPv6FilterParamsDestPortValue1 OBJECT-TYPE
    SYNTAX      TTcpUdpPort
    MAX-ACCESS  read-create
    STATUS      current
    DESCRIPTION
        "TCP/UDP port value1. The value of this object is used as per the
         description for tIPv6FilterParamsDestPortOperator."
    DEFVAL { 0 }
    ::= { tIPv6FilterParamsEntry 19 }

tIPv6FilterParamsDestPortValue2 OBJECT-TYPE
    SYNTAX      TTcpUdpPort
    MAX-ACCESS  read-create
    STATUS      current
    DESCRIPTION
        "TCP/UDP port value2. The value of this object is used as per the
         description for tIPv6FilterParamsDestPortOperator."
    DEFVAL { 0 }
    ::= { tIPv6FilterParamsEntry 20 }

tIPv6FilterParamsDestPortOperator OBJECT-TYPE
    SYNTAX      TOperator
    MAX-ACCESS  read-create
    STATUS      current
    DESCRIPTION
        "The operator specifies the manner in which
         tIPFilterParamsDestPortValue1 and tIPFilterParamsDestPortValue2 are to
         be used."
    DEFVAL { none }
    ::= { tIPv6FilterParamsEntry 21 }

tIPv6FilterParamsDSCP OBJECT-TYPE
    SYNTAX      TDSCPNameOrEmpty
    MAX-ACCESS  read-create
    STATUS      current
    DESCRIPTION
        "DSCP to be matched on the packet."
    DEFVAL { ''H }
    ::= { tIPv6FilterParamsEntry 22 }

tIPv6FilterParamsTcpSyn OBJECT-TYPE
    SYNTAX      TItemMatch
    MAX-ACCESS  read-create
    STATUS      current
    DESCRIPTION
        "If Enabled, matches a TCP Syn as per value of the object."
    DEFVAL { off }
    ::= { tIPv6FilterParamsEntry 23 }

tIPv6FilterParamsTcpAck OBJECT-TYPE
    SYNTAX      TItemMatch
    MAX-ACCESS  read-create
    STATUS      current
    DESCRIPTION
        "If Enabled, matches a TCP Ack as per value of the object."
    DEFVAL { off }
    ::= { tIPv6FilterParamsEntry 24 }

tIPv6FilterParamsIcmpCode OBJECT-TYPE
    SYNTAX      INTEGER (-1|0..255)
    MAX-ACCESS  read-create
    STATUS      current
    DESCRIPTION
        "Icmp code to be matched. tIPv6FilterParamsIcmpCode complements the
         object tIPv6FilterParamsIcmpType. Both of them need to be set to
         actually enable ICMP matching. The value -1 means Icmp code matching
         is not enabled."
    DEFVAL { -1 }
    ::= { tIPv6FilterParamsEntry 25 }

tIPv6FilterParamsIcmpType OBJECT-TYPE
    SYNTAX      INTEGER (-1|0..255)
    MAX-ACCESS  read-create
    STATUS      current
    DESCRIPTION
        "Icmp type to be matched. tIPv6FilterParamsIcmpType complements the
         object tIPv6FilterParamsIcmpCode. Both of them need to be set to
         actually enable ICMP matching. The value -1 means Icmp type matching is
         not enabled."
    DEFVAL { -1 }
    ::= { tIPv6FilterParamsEntry 26 }

tIPv6FilterParamsCflowdSample OBJECT-TYPE
    SYNTAX      TruthValue
    MAX-ACCESS  read-create
    STATUS      current
    DESCRIPTION
        "When tIPFilterParamsCflowdSample has a value of 'true',  Cflowd
         sampling and analysis is performed on those packet streams where this
         filter has been applied.  Only packets matching this IPv6 filter entry
         are subjected to Cflowd sampling and analysis.  A Cflowd profile
         controls the sampling and analysis of data flows through the router."
    DEFVAL { false }
    ::= { tIPv6FilterParamsEntry 27 }

tIPv6FilterParamsCflowdIfSample OBJECT-TYPE
    SYNTAX      TruthValue
    MAX-ACCESS  read-create
    STATUS      current
    DESCRIPTION
        "When tIPv6FilterParamsCflowdIfSample has a value of 'true', Cflowd
         sampling and analysis is performed on those packet streams where this
         filter has been applied.  Only packets matching this IPv6 filter entry
         are subjected to Cflowd sampling and analysis.  A Cflowd profile
         controls the sampling and analysis of data flows through the router."
    DEFVAL { true }
    ::= { tIPv6FilterParamsEntry 28 }

tIPv6FilterParamsForwardNHInterface OBJECT-TYPE
    SYNTAX      DisplayString (SIZE(0..32))
    MAX-ACCESS  read-create
    STATUS      current
    DESCRIPTION
        "The interface name for the nexthop to which the packet should be
         forwarded if it hits this filter entry. The action of this entry
         should be 'forward' in such a case.

         Note that the value of tIPv6FilterParamsForwardNHInterface  is silently
         cleared by the system if tIPv6FilterParamsAction is set to value other
         than 'forward'(2), or any object related to 'forward' other than
         this one is set."
    DEFVAL { ''H }
    ::= { tIPv6FilterParamsEntry 29 }

tIPv6FilterParamsIngressHitCount OBJECT-TYPE
    SYNTAX      Counter64
    MAX-ACCESS  read-only
    STATUS      current
    DESCRIPTION
        "This object indicates the number of times an ingress packet
         matched this entry."
    ::= { tIPv6FilterParamsEntry 30 }

tIPv6FilterParamsEgressHitCount OBJECT-TYPE
    SYNTAX      Counter64
    MAX-ACCESS  read-only
    STATUS      current
    DESCRIPTION
        "This object indicates the number of times an egress packet
         matched this entry."
    ::= { tIPv6FilterParamsEntry 31 }

tIPv6FilterParamsLogInstantiated OBJECT-TYPE
    SYNTAX      TruthValue
    MAX-ACCESS  read-only
    STATUS      current
    DESCRIPTION
        "tIPv6FilterParamsLogInstantiated indicates if the filter log for
         this filter entry has been instantiated or not."
    ::= { tIPv6FilterParamsEntry 32 }

tIPv6FilterParamsForwardRedPlcy OBJECT-TYPE
    SYNTAX      TNamedItemOrEmpty
    MAX-ACCESS  read-create
    STATUS      current
    DESCRIPTION
        "tIPv6FilterParamsForwardRedPlcy specifies the redirect policy to be
         used to determine the nexthop.

         Note that the value of tIPv6FilterParamsForwardRedPlcy is silently
         cleared by the system if tIPv6FilterParamsAction is set to value other
         than 'forward'(2), or any object related to 'forward' other than
         this one is set."
    DEFVAL { ''H }
    ::= { tIPv6FilterParamsEntry 33 }

tIPv6FilterParamsActiveDest OBJECT-TYPE
    SYNTAX      InetAddressIPv6
    MAX-ACCESS  read-only
    STATUS      current
    DESCRIPTION
        "tIPv6FilterParamsActiveDest indicates the IPv6 address of the active
         destination for this IPv6 filter. A value of 0 indicates that there
         is currently no active destination."
    ::= { tIPv6FilterParamsEntry 34 }

tIPv6FilterParamsTimeRangeName OBJECT-TYPE
    SYNTAX      TNamedItemOrEmpty
    MAX-ACCESS  read-create
    STATUS      obsolete
    DESCRIPTION
        "tIPv6FilterParamsTimeRangeName specifies the tmnxTimeRangeEntry to be
         associated with this filter entry.

         A value for this object can only be specified during row creation, and
         cannot be altered later on.
         Also, a value is accepted only if the tmnxTimeRangeEntry is defined in
         the TIMETRA-SCHEDULER-MIB::tmnxTimeRangeTable.tTimeRangeName.

         This object is obsoleted in release 14.0."
    DEFVAL { ''H }
    ::= { tIPv6FilterParamsEntry 35 }

tIPv6FilterParamsTimeRangeState OBJECT-TYPE
    SYNTAX      TTimeRangeState
    MAX-ACCESS  read-only
    STATUS      obsolete
    DESCRIPTION
        "tIPv6FilterParamsTimeRangeState indicates whether or not the entry
         is currently in effect.
         - timeRangeNotApplic:
           no time range is applicable for this entry.
         - timeRangeNotActive:
           A time range is defined in tIPv6FilterParamsTimeRangeName, but is not
           active at this moment. Consequently the filter entry is not
           installed.
         - timeRangeActive.
           A time range is defined in tIPv6FilterParamsTimeRangeName, and is
           activated successfully.
         - timeRangeActiveDownloadFailed:
           A time range is defined in tIPv6FilterParamsTimeRangeName, and is
           activated, but the corresponding filter entry could not be
           installed due to resource problems.

         This object is obsoleted in release 14.0."
    ::= { tIPv6FilterParamsEntry 36 }

tIPv6FilterParamsIngrHitByteCount OBJECT-TYPE
    SYNTAX      Counter64
    MAX-ACCESS  read-only
    STATUS      current
    DESCRIPTION
        "The value of tIPv6FilterParamsIngrHitByteCount indicates the number
         of bytes of all ingress packets that matched this entry."
    ::= { tIPv6FilterParamsEntry 37 }

tIPv6FilterParamsEgrHitByteCount OBJECT-TYPE
    SYNTAX      Counter64
    MAX-ACCESS  read-only
    STATUS      current
    DESCRIPTION
        "This tIPv6FilterParamsEgrHitByteCount indicates the number
         of bytes of all egress packets that matched this entry."
    ::= { tIPv6FilterParamsEntry 38 }

tIPv6FilterParamsFwdSvcId OBJECT-TYPE
    SYNTAX      TmnxServId
    MAX-ACCESS  read-only
    STATUS      current
    DESCRIPTION
        "tIPv6FilterParamsFwdSvcId indicates the service id of the
         destination for this filter entry. The value 0 indicates that
         there is no active SAP or SDP destination."
    ::= { tIPv6FilterParamsEntry 39 }

tIPv6FilterParamsFwdSapPortId OBJECT-TYPE
    SYNTAX      TmnxPortID
    MAX-ACCESS  read-create
    STATUS      current
    DESCRIPTION
        "tIPv6FilterParamsFwdSapPortId specifies the sap port id of the
         destination for this filter entry.

         The value 0 indicates that there is no SAP destination
         defined. A value different from 0 can only be specified if the value
         of the tIPv6FilterParamsAction object of this entry is 'forward'.
         In addition a non-zero value can only be given if the object
         tIPv6FilterParamsFwdSdpBind is '0'.

         Note that the value of tIPv6FilterParamsFwdSapPortId is silently
         cleared by the system if tIPv6FilterParamsAction is set to
         value other than 'forward'(2), or any object related to 'forward'
         other than tIPv6FilterParamsFwdSapPortId or
         tIPv6FilterParamsFwdSapEncapVal is set."
    DEFVAL { 0 }
    ::= { tIPv6FilterParamsEntry 40 }

tIPv6FilterParamsFwdSapEncapVal OBJECT-TYPE
    SYNTAX      TmnxEncapVal
    MAX-ACCESS  read-create
    STATUS      current
    DESCRIPTION
        "tIPv6FilterParamsFwdSapEncapVal specifies the sap port encap value
         of the destination SAP for this filter entry.

         A value different from 0 can only be specified if the value of the
         tIPv6FilterParamsAction object of this entry is 'forward'. In addition
         a non-zero value can only be given if the object
         tIPv6FilterParamsFwdSdpBind has value '0'. The value 0 indicates
         that either
         1) the sap encapsulation value is not specified when
            tIPv6FilterParamsFwdSapPortId and tIPv6FilterParamsFwdSvcId
            have valid values; or
         2) that there is no SAP destination.

         Note that the value of tIPv6FilterParamsFwdSapEncapVal is silently
         cleared by the system if tIPv6FilterParamsAction is set to
         value other than 'forward'(2), or any object related to 'forward'
         other than tIPv6FilterParamsFwdSapPortId or
         tIPv6FilterParamsFwdSapEncapVal is set."
    DEFVAL { 0 }
    ::= { tIPv6FilterParamsEntry 41 }

tIPv6FilterParamsFwdSdpBind OBJECT-TYPE
    SYNTAX      SdpBindId
    MAX-ACCESS  read-create
    STATUS      current
    DESCRIPTION
        "tIPv6FilterParamsFwdSdpBind specifies the sdp bind id of the
         destination for this filter entry.

         The value '0' indicates that there is currently no SDP binding defined.
         A value different from '0' can only be specified if the value of the
         tIPv6FilterParamsAction object of this entry is 'forward'. In addition
         a non-zero value can only be given if the objects
         tIPv6FilterParamsFwdSapPortId and tIPv6FilterParamsFwdSapEncapVal have
         value 0.

         Note that the value of tIPv6FilterParamsFwdSdpBind is silently cleared
         by the system if tIPv6FilterParamsAction is set to
         value other than 'forward'(2), or any object related to 'forward'
         other than this one is set."
    DEFVAL { '0000000000000000'H }
    ::= { tIPv6FilterParamsEntry 42 }

tIPv6FilterParamsRedirectURL OBJECT-TYPE
    SYNTAX      TmnxHttpRedirectUrl
    MAX-ACCESS  read-create
    STATUS      current
    DESCRIPTION
        "The value of tIPv6FilterParamsRedirectURL specifies the URL
         to redirect to, when the value of tIPv6FilterParamsAction is
         'httpRedirect'.

         The following macro substitutions are applicable in this context:
         $URL, $MAC, $IP, $SUB, $SAP, $SAPDESC, $CID, and $RID.

         Note that the value of tIPv6FilterParamsRedirectURL is silently
         cleared by the system if tIPv6FilterParamsAction is set to any value
         other than httpRedirect."
    DEFVAL { ''H }
    ::= { tIPv6FilterParamsEntry 43 }

tIPv6FilterParamsSrcIpPrefixList OBJECT-TYPE
    SYNTAX      TNamedItemOrEmpty
    MAX-ACCESS  read-create
    STATUS      current
    DESCRIPTION
        "The value of this object specifies the ipv6-prefix-list used as match
         criterion for the source ipv6 address.

         The value specified for this object must correspond to a prefix-list
         defined in tFilterPrefixListTable.

         If the value of this object is empty then the values of the objects
         tIPv6FilterParamsSourceIpAddr and tIPv6FilterParamsSourceIpMask are
         used as source ipv6 address match criterion.

         When this object is set to a non-empty value then the objects
         tIPv6FilterParamsSourceIpAddr and tIPv6FilterParamsSourceIpMask are
         reset to their default values by the system.

         Vice versa, when a new (non-default) value is provided for the objects
         tIPv6FilterParamsSourceIpAddr and tIPv6FilterParamsSourceIpMask then
         this object is reset to its default (empty) value by the system."
    DEFVAL { ''H }
    ::= { tIPv6FilterParamsEntry 44 }

tIPv6FilterParamsDstIpPrefixList OBJECT-TYPE
    SYNTAX      TNamedItemOrEmpty
    MAX-ACCESS  read-create
    STATUS      current
    DESCRIPTION
        "The value of this object specifies the ipv6-prefix-list used as match
         criterion for the destination ipv6 address.

         The value specified for this object must correspond to a prefix-list
         defined in tFilterPrefixListTable.

         If the value of this object is empty then the values of the objects
         tIPv6FilterParamsDestinationIpAddr and
         tIPv6FilterParamsDestinationIpMask are used as destination ipv6
         address match criterion.

         When this object is set to a non-empty value then the objects
         tIPv6FilterParamsDestinationIpAddr and
         tIPv6FilterParamsDestinationIpMask are reset to their default values by
         the system.

         Vice versa, when a new (non-default) value is provided for the objects
         tIPv6FilterParamsDestinationIpAddr and
         tIPv6FilterParamsDestinationIpMask
         then this object is reset to its default (empty) value by the system."
    DEFVAL { ''H }
    ::= { tIPv6FilterParamsEntry 45 }

 tIPv6FilterParamsFragment OBJECT-TYPE
    SYNTAX INTEGER {
                     off (1),
                     false (2),
                     true (3),
                     first-only (4),
                     non-first-only (5)
                   }
    MAX-ACCESS  read-create
    STATUS      current
    DESCRIPTION
        "If Enabled, matches fragmented/unfragmented packets as per value of
         the object."
     DEFVAL { off }
    ::= { tIPv6FilterParamsEntry 46 }

 tIPv6FilterParamsHopByHopOpt OBJECT-TYPE
    SYNTAX      TItemMatch
    MAX-ACCESS  read-create
    STATUS      current
    DESCRIPTION
        "If Enabled, matches a Hop-By-Hop options Extension Header as per value
         of the object."
    DEFVAL { off }
    ::= { tIPv6FilterParamsEntry 47 }

 tIPv6FilterParamsRoutingType0 OBJECT-TYPE
    SYNTAX      TItemMatch
    MAX-ACCESS  read-create
    STATUS      current
    DESCRIPTION
        "If Enabled, matches a Routing Extension Header as per value of the
         object."
    DEFVAL { off }
    ::= { tIPv6FilterParamsEntry 48 }

tIPv6FilterParamsPortSelector OBJECT-TYPE
    SYNTAX      TFltrPortSelector
    MAX-ACCESS  read-create
    STATUS      current
    DESCRIPTION
        "This object specifies how the source-port objects
         (tIPv6FilterParamsSourcePortValue1, tIPv6FilterParamsSourcePortValue2,
         tIPv6FilterParamsSourcePortOperator, tIPv6FilterParamsSrcPortList)
         and destination-port objects (tIPv6FilterParamsDestPortValue1,
         tIPv6FilterParamsDestPortValue2, tIPv6FilterParamsDestPortOperator,
         tIPv6FilterParamsDstPortList) are combined to form the filter match
         criterion. See description of TFltrPortSelector."
    DEFVAL { and-port }
    ::= { tIPv6FilterParamsEntry 49 }

tIPv6FilterParamsSrcPortList OBJECT-TYPE
    SYNTAX      TNamedItemOrEmpty
    MAX-ACCESS  read-create
    STATUS      current
    DESCRIPTION
        "The value of this object specifies the port-list used as match
         criterion for the source port.

         The value specified for this object must correspond to a port-list
         defined in tFilterPortListTable.

         If the value of this object is empty then the values of the objects
         tIPFilterParamsSourcePortValue1, tIPFilterParamsSourcePortValue2, and
         tIPFilterParamsSourcePortOperator are used as source port match
         criterion.

         When this object is set to a non-empty value then the objects
         tIPFilterParamsSourcePortValue1, tIPFilterParamsSourcePortValue2, and
         tIPFilterParamsSourcePortOperator are reset to their default values by
         the system.

         Vice versa, when a new (non-default) value is provided for one of the
         objects tIPFilterParamsSourcePortValue1,
         tIPFilterParamsSourcePortValue2, or tIPFilterParamsSourcePortOperator
         then tIPv6FilterParamsSrcPortList is reset to its default (empty) value
         by the system.

         Setting any one of the objects tIPFilterParamsSourcePortValue1,
         tIPFilterParamsSourcePortValue2, or tIPFilterParamsSourcePortOperator
         to a non-default value in combination with a non-default value for the
         object tIPv6FilterParamsSrcPortList is rejected by the system"
    DEFVAL { ''H }
    ::= { tIPv6FilterParamsEntry 50 }

tIPv6FilterParamsDstPortList OBJECT-TYPE
    SYNTAX      TNamedItemOrEmpty
    MAX-ACCESS  read-create
    STATUS      current
    DESCRIPTION
        "The value of this object specifies the port-list used as match
         criterion for the destination port.

         The value specified for this object must correspond to a port-list
         defined in tFilterPortListTable.

         If the value of this object is empty then the values of the objects
         tIPFilterParamsDestPortValue1, tIPFilterParamsDestPortValue2, and
         tIPFilterParamsDestPortOperator are used as destination port match
         criterion.

         When this object is set to a non-empty value then the objects
         tIPFilterParamsDestPortValue1, tIPFilterParamsDestPortValue2, and
         tIPFilterParamsDestPortOperator are reset to their default values by
         the system.

         Vice versa, when a new (non-default) value is provided for one of the
         objects tIPFilterParamsDestPortValue1, tIPFilterParamsDestPortValue2,
         or tIPFilterParamsDestPortOperator then tIPv6FilterParamsDstPortList is
         reset to its default (empty) value by the system.

         Setting any one of the objects tIPFilterParamsDestPortValue1,
         tIPFilterParamsDestPortValue2, or tIPFilterParamsDestPortOperator to a
         non-default value in combination with a non-default value for the
         object tIPv6FilterParamsDstPortList is rejected by the system"
    DEFVAL { ''H }
    ::= { tIPv6FilterParamsEntry 51 }

tIPv6FilterParamsRdirAllwRadOvrd OBJECT-TYPE
    SYNTAX      TruthValue
    MAX-ACCESS  read-create
    STATUS      current
    DESCRIPTION
        "The value of this object specifies whether or not the value of
         tIPv6FilterParamsRedirectURL can be over-ridden by a Radius VSA. The
         default value is false (i.e. the URL cannot be over-ridden by Radius).
         The value of tIPv6FilterParamsRdirAllwRadOvrd is relevant only if the
         value of tIPv6FilterParamsAction is httpRedirect.

         Setting the value of tIPv6FilterParamsRdirAllwRadOvrd to true is
         ignored by the system if the value of tIPv6FilterParamsAction is not
         httpRedirect. Furthermore, the value of
         tIPv6FilterParamsRdirAllwRadOvrd is silently reset to false by the
         system if tIPv6FilterParamsAction is set to any value other than
         httpRedirect."
    DEFVAL { false }
    ::= { tIPv6FilterParamsEntry 52 }

tIPv6FilterParamsFwdRtrId OBJECT-TYPE
    SYNTAX      TmnxVRtrIDOrZero
    MAX-ACCESS  read-create
    STATUS      current
    DESCRIPTION
        "tIPv6FilterParamsFwdRtrId specifies, if different from '0',
         the router id into which the packet should be forwarded
         if it hits this filter entry.

         The action of this entry should be 'forward' in such a case.

         Note that the value of tIPv6FilterParamsFwdRtrId is silently
         cleared by the system if tIPv6FilterParamsAction is set to
         value other than 'forward'(2), or any object related to 'forward'
         other than tIPv6FilterParamsFwdRtrId, tIPv6FilterParamsForwardNH
         or tIPv6FilterParamsForwardNHIndirect is set."
    DEFVAL { 0 }
    ::= { tIPv6FilterParamsEntry 53 }

tIPv6FilterParamsSrcIpFullMask OBJECT-TYPE
    SYNTAX      InetAddressIPv6
    MAX-ACCESS  read-create
    STATUS      current
    DESCRIPTION
        "If different from 0, the object tIPv6FilterParamsSrcIpFullMask
         specifies the IPv6 Mask value for this policy IPv6 Filter entry.
         The mask is ANDed with the received Source IPv6 address to match
         the tIPv6FilterParamsSourceIpAddr.
         
         If the value of tIPv6FilterParamsSourceIpMask is 0, and the
         value of tIPv6FilterParamsSrcIpFullMask is non zero then the
         value of tIPv6FilterParamsSrcIpFullMask is used as a mask.

         If the value of tIPv6FilterParamsSourceIpMask is non zero,
         it will be equal to the mask expressed in the object
         tIPv6FilterParamsSrcIpFullMask.

         If both tIPv6FilterParamsSourceIpMask and
         tIPv6FilterParamsSrcIpFullMask are set to 0, no matching is done
         on the Source IPv6 address.

         If a regular mask is specified for tIPv6FilterParamsSrcIpFullMask
         then the value of tIPv6FilterParamsSourceIpMask will be changed
         to reflect this value."
    DEFVAL { '00000000000000000000000000000000'H }
    ::= { tIPv6FilterParamsEntry 54 }

tIPv6FilterParamsDstIpFullMask OBJECT-TYPE
    SYNTAX      InetAddressIPv6
    MAX-ACCESS  read-create
    STATUS      current
    DESCRIPTION
        "If different from 0, the object tIPv6FilterParamsDstIpFullMask
         specifies the IPv6 Mask value for this policy IPv6 Filter entry.
         The mask is ANDed with the received Destination IPv6 address to match
         the tIPv6FilterParamsDestinationIpAddr.
         
         If the value of tIPv6FilterParamsDestinationIpMask is 0, and the
         value of tIPv6FilterParamsDstIpFullMask is non zero then the
         value of tIPv6FilterParamsDstIpFullMask is used as a mask.

         If the value of tIPv6FilterParamsDestinationIpMask is non zero,
         it will be equal to the mask expressed in the object
         tIPv6FilterParamsDstIpFullMask.

         If both tIPv6FilterParamsDestinationIpMask and
         tIPv6FilterParamsDstIpFullMask are set to 0, no matching is done
         on the Destination IPv6 address.

         If a regular mask is specified for tIPv6FilterParamsDstIpFullMask
         then the value of tIPv6FilterParamsDestinationIpMask will be changed
         to reflect this value."
    DEFVAL { '00000000000000000000000000000000'H }
    ::= { tIPv6FilterParamsEntry 55 }

tIPv6FilterParamsNatPolicyName OBJECT-TYPE
    SYNTAX      TNamedItemOrEmpty
    MAX-ACCESS  read-create
    STATUS      current
    DESCRIPTION
        "The value of this object specifies the name of the NAT policy to be
         used when the value of tIPv6FilterParamsAction is nat. If the value is
         empty then a default policy is used. If the value is non-empty then it
         must correspond to a policy defined in tmnxNatPlcyTable.

         The value of tIPv6FilterParamsNatPolicyName is relevant only if the
         value of tIPv6FilterParamsAction is nat. Setting the value of
         tIPv6FilterParamsNatPolicyName to a non-empty string is ignored by the
         system if the value of tIPv6FilterParamsAction is not nat.

         Furthermore, the value of tIPv6FilterParamsNatPolicyName is silently
         reset to an empty string by the system if tIPv6FilterParamsAction is
         set to any value other than nat."
    DEFVAL { "" }
    ::= { tIPv6FilterParamsEntry 56 }

tIPv6FilterParamsFlowLabel OBJECT-TYPE
    SYNTAX      IPv6FlowLabel
    MAX-ACCESS  read-create
    STATUS      current
    DESCRIPTION
         "If different from -1 the value of the object
          tIPv6FilterParamsFlowLabel specifies the flow label
          to be used as a match criterion."
    DEFVAL { -1 }
    ::= { tIPv6FilterParamsEntry 57 }

tIPv6FilterParamsFlowLabelMask OBJECT-TYPE
    SYNTAX      IPv6FlowLabelMask
    MAX-ACCESS  read-create
    STATUS      current
    DESCRIPTION
         "The value of the object tIPv6FilterParamsFlowLabelMask
          specifies the flow label mask value for this policy IP Filter entry.

          The mask is ANDed with the received flow label to match
          the value of the object tIPv6FilterParamsFlowLabel.

          The value is only significant if the value of the object
          tIPv6FilterParamsFlowLabel is different from -1."
    DEFVAL { '0fffff'H }
    ::= { tIPv6FilterParamsEntry 58 }

tIPv6FilterParamsFwdLsp OBJECT-TYPE
    SYNTAX      TmnxVRtrMplsLspID (0..65535)
    MAX-ACCESS  read-create
    STATUS      current
    DESCRIPTION
         "If different from zero the value of the object tIPv6FilterParamsFwdLsp
          together with the value of the object tIPv6FilterParamsFwdLspRtrId
          specifies the LSP into which a packet should be forwarded if it hits
          this filter entry.

          The value of the object tIPv6FilterParamsAction of this entry
          must be 'forward' in such case. Otherwise the value of the object
          tIPv6FilterParamsFwdLsp is ignored by the system.

          The value is reset to '0' if the value of the object
          tIPv6FilterParamsAction is set to value other than 'forward'(2),
          or any object related to 'forward' other than
          tIPv6FilterParamsFwdLspRtrId or tIPv6FilterParamsFwdLsp is set.

          The value of the object tIPv6FilterParamsFwdLsp cannot be set to a
          non-zero value if other destinations are already specified.

          The value has to be '0' if the value of the object
          tIPv6FilterParamsFwdLspRtrId is not set (i.e. is '0').

          If a non-zero value is set, the value of the object
          tIPv6FilterParamsFwdLspRtrId has to be set as well."
    DEFVAL { 0 }
    ::= { tIPv6FilterParamsEntry 59 }

tIPv6FilterParamsFwdLspRtrId OBJECT-TYPE
    SYNTAX      TmnxVRtrIDOrZero
    MAX-ACCESS  read-create
    STATUS      current
    DESCRIPTION
         "The value of the object tIPv6FilterParamsFwdLspRtrId specifies
          the router ID that the LSP ID defined by the value of the object
          tIPv6FilterParamsFwdLsp belongs to.

          The value of the object tIPv6FilterParamsAction of this entry
          must be 'forward' in such case. Otherwise the value of the object
          tIPv6FilterParamsFwdLspRtrId is ignored by the system.

          The value is reset to '0' if the value of the object
          tIPv6FilterParamsAction is set to other value than 'forward'(2),
          or any object related to 'forward' other than
          tIPv6FilterParamsFwdLspRtrId or tIPv6FilterParamsFwdLsp is set.

          The value of this object cannot be set to a non-zero value if
          other destinations are already specified.

          The value has to be '0' if the value of the object
          tIPv6FilterParamsFwdLsp is not set (i.e. is '0').

          If a non-zero value is set, the value of the object
          tIPv6FilterParamsFwdLsp has to be set as well.

          The ID of the base router and '0' are the only allowed values
          with this version of the product."
    DEFVAL { 0 }
    ::= { tIPv6FilterParamsEntry 60 }

--
-- SNMP objects allowing to group filter entries that are inserted in a filter
-- by either radius or Credit Control.
--

tFilterGroupInsertedEntries  OBJECT IDENTIFIER ::= { tFilterObjects 20 }

tFltrGrpInsrtdEntriesFilterType OBJECT-TYPE
    SYNTAX      TFilterType
    MAX-ACCESS  read-write
    STATUS      current
    DESCRIPTION
        "tFltrGrpInsrtdEntriesFilterType specifies the type of the filter
         referred to by tFltrGrpInsrtdEntriesFilterId.
         Inserted entries can only occur in 'fltrtypeselIp' and
         'fltrtypeselIpv6'"
    DEFVAL { fltrtypeselNone }
    ::= { tFilterGroupInsertedEntries 1 }

tFltrGrpInsrtdEntriesFilterId OBJECT-TYPE
    SYNTAX      TFilterID
    MAX-ACCESS  read-write
    STATUS      current
    DESCRIPTION
        "tFltrGrpInsrtdEntriesFilterId specifies for which filter the inserted
         entries must be grouped."
    DEFVAL { 0 }
    ::= { tFilterGroupInsertedEntries 2 }

tFltrGrpInsrtdEntriesApplication OBJECT-TYPE
    SYNTAX      TFilterSubInsSpaceOwner
    MAX-ACCESS  read-write
    STATUS      current
    DESCRIPTION
        "tFltrGrpInsrtdEntriesApplication specifies for which application
         the inserted entries must be grouped."
    DEFVAL { none }
    ::= { tFilterGroupInsertedEntries 3 }

tFltrGrpInsrtdEntriesLocation OBJECT-TYPE
    SYNTAX INTEGER {
                     none     (0),
                     top      (1),
                     bottom   (2)
                   }
    MAX-ACCESS  read-write
    STATUS      current
    DESCRIPTION
        "tFltrGrpInsrtdEntriesLocation specifies at what location the inserted
         entries must be grouped."
    DEFVAL { none }
    ::= { tFilterGroupInsertedEntries 4 }

tFltrGrpInsrtdEntriesResult OBJECT-TYPE
    SYNTAX INTEGER {
                     none     (0),
                     success  (1),
                     failure  (2)
                   }
    MAX-ACCESS  read-only
    STATUS      current
    DESCRIPTION
        "tFltrGrpInsrtdEntriesResult indicates the success or failure of the
         last requested grouping request on inserted entries."
    ::= { tFilterGroupInsertedEntries 5 }

tFltrGrpInsrtdEntriesFeedback OBJECT-TYPE
    SYNTAX      DisplayString (SIZE (0..254))
    MAX-ACCESS  read-only
    STATUS      current
    DESCRIPTION
        "tFltrGrpInsrtdEntriesFeedback may indicate additional info on the last
         inserted filter entries grouping action performed."
    ::= { tFilterGroupInsertedEntries 6 }

tFltrGrpInsrtdEntriesExecute OBJECT-TYPE
    SYNTAX      TruthValue
    MAX-ACCESS  read-write
    STATUS      current
    DESCRIPTION
        "Setting the object tFltrGrpInsrtdEntriesExecute to 'true' will cause
         the system to attempt to execute the grouping command as specified
         by the other MIB objects in the tFilterGroupInsertedEntries mibgroup.

         When read the value will always indicate 'false'. The result of the
         command can be found in tFltrGrpInsrtdEntriesResult and
         tFltrGrpInsrtdEntriesFeedback"
    DEFVAL { false }
    ::= { tFilterGroupInsertedEntries 7 }

--
-- DHCP filter table
--

tDhcpFilterTableLastChanged OBJECT-TYPE
    SYNTAX      TimeStamp
    MAX-ACCESS  read-only
    STATUS      current
    DESCRIPTION
        "The value of tDhcpFilterTableLastChanged indicates the sysUpTime
         at the time of the last modification to tDhcpFilterTable by
         adding, deleting an entry or change to a writable object in the table.

         If no changes were made to the table since the last re-initialization
         of the local network management subsystem, then this object contains a
         zero value."
    ::= { tFilterObjects 21 }

tDhcpFilterTable OBJECT-TYPE
    SYNTAX      SEQUENCE OF TDhcpFilterEntry
    MAX-ACCESS  not-accessible
    STATUS      current
    DESCRIPTION
        "Contains a list of all DHCP filters configured on this system."
    ::= { tFilterObjects 22 }

tDhcpFilterEntry OBJECT-TYPE
    SYNTAX      TDhcpFilterEntry
    MAX-ACCESS  not-accessible
    STATUS      current
    DESCRIPTION
        "Information about a particular DHCP filter. Entries are created/deleted
         by user. Entries have a presumed StorageType of nonVolatile."
    INDEX { tDhcpFilterId }
    ::= { tDhcpFilterTable 1 }

TDhcpFilterEntry ::= SEQUENCE
    {
        tDhcpFilterId           TDHCPFilterID,
        tDhcpFilterRowStatus    RowStatus,
        tDhcpFilterLastChanged  TimeStamp,
        tDhcpFilterDescription  TItemDescription
      , tDhcpFilterDefAction    TDhcpFilterAction
    }

tDhcpFilterId OBJECT-TYPE
    SYNTAX      TDHCPFilterID (1..65535)
    MAX-ACCESS  not-accessible
    STATUS      current
    DESCRIPTION
        "Uniquely identifies a DHCP filter as configures on this system."
    ::= { tDhcpFilterEntry 1 }

tDhcpFilterRowStatus OBJECT-TYPE
    SYNTAX      RowStatus
    MAX-ACCESS  read-create
    STATUS      current
    DESCRIPTION
        "This object allows entries to be created and deleted in the
         tDhcpFilterTable."
    ::= { tDhcpFilterEntry 2 }

tDhcpFilterLastChanged OBJECT-TYPE
    SYNTAX      TimeStamp
    MAX-ACCESS  read-only
    STATUS      current
    DESCRIPTION
        "The value of tDhcpFilterLastChanged indicates the timestamp of
         last change to this row in tDhcpFilterTable."
    ::= { tDhcpFilterEntry 3 }

tDhcpFilterDescription OBJECT-TYPE
    SYNTAX      TItemDescription
    MAX-ACCESS  read-create
    STATUS      current
    DESCRIPTION
        "User-provided description for this filter."
    DEFVAL { ''H }
    ::= { tDhcpFilterEntry 4 }

tDhcpFilterDefAction OBJECT-TYPE
    SYNTAX      TDhcpFilterAction
    MAX-ACCESS  read-create
    STATUS      current
    DESCRIPTION
        "The default action to take for DHCP host creation requests that do
         not match any of this filter's entries.
         
         The value none(1) specifies normal host creation behaviour, the value
         bypass-host-creation(2) specifies to bypass host creation, the value
         drop(3) specifies to drop the DHCP message."
    DEFVAL { none }
    ::= { tDhcpFilterEntry 5 }

--
-- DHCP Filter Entry parameters
--

tDhcpFilterParamsTblLastChanged OBJECT-TYPE
    SYNTAX      TimeStamp
    MAX-ACCESS  read-only
    STATUS      current
    DESCRIPTION
        "The value of tDhcpFilterParamsTblLastChanged indicates the sysUpTime
         at the time of the last modification to tDhcpFilterParamsTable by
         adding, deleting an entry or change to a writable object in the table.

         If no changes were made to the table since the last re-initialization
         of the local network management subsystem, then this object contains a
         zero value."
    ::= { tFilterObjects 23 }

tDhcpFilterParamsTable OBJECT-TYPE
    SYNTAX      SEQUENCE OF TDhcpFilterParamsEntry
    MAX-ACCESS  not-accessible
    STATUS      current
    DESCRIPTION  "A table of all DHCP filter match entries for all DHCP filters"
    ::= { tFilterObjects 24 }

tDhcpFilterParamsEntry OBJECT-TYPE
    SYNTAX      TDhcpFilterParamsEntry
    MAX-ACCESS  not-accessible
    STATUS      current
    DESCRIPTION
        "Information about a particular DHCP filter entry.
        Every DHCP filter can have zero or more DHCP filter match entries.

        A filter entry with no match criteria set will match every
        packet, and the entry action will be taken.

        Entries are created/deleted by user.

        There is no StorageType object, entries have a presumed
        StorageType of nonVolatile."
    INDEX { tDhcpFilterId, tDhcpFilterParamsId }
    ::= { tDhcpFilterParamsTable 1 }

TDhcpFilterParamsEntry ::= SEQUENCE
    {
        tDhcpFilterParamsId              TEntryId,
        tDhcpFilterParamsRowStatus       RowStatus,
        tDhcpFilterParamsLastChanged     TimeStamp,
        tDhcpFilterParamsOptionNumber    INTEGER,
        tDhcpFilterParamsOptionMatch     TDhcpFilterMatch,
        tDhcpFilterParamsAction          TDhcpFilterAction,
        tDhcpFilterParamsOptionValue     OCTET STRING
    }

tDhcpFilterParamsId OBJECT-TYPE
    SYNTAX      TEntryId
    MAX-ACCESS  not-accessible
    STATUS      current
    DESCRIPTION
        "This is the secondary index for the entry. Every DHCP filter can have
         multiple entries, therefore every DHCP filter entry is identified by
         the tDhcpFilterId and tDhcpFilterParamsId."
    ::= { tDhcpFilterParamsEntry 1 }

tDhcpFilterParamsRowStatus OBJECT-TYPE
    SYNTAX      RowStatus
    MAX-ACCESS  read-create
    STATUS      current
    DESCRIPTION
        "This object allows entries to be created and deleted in the
         tDhcpFilterParamsTable."
    ::= { tDhcpFilterParamsEntry 2 }

tDhcpFilterParamsLastChanged OBJECT-TYPE
    SYNTAX      TimeStamp
    MAX-ACCESS  read-only
    STATUS      current
    DESCRIPTION
        "The value of tDhcpFilterParamsLastChanged indicates the timestamp of
         last change to this row in tDhcpFilterParamsTable."
    ::= { tDhcpFilterParamsEntry 3 }

tDhcpFilterParamsOptionNumber OBJECT-TYPE
    SYNTAX      INTEGER (-1|0..255)
    MAX-ACCESS  read-create
    STATUS      current
    DESCRIPTION
        "The value of tDhcpFilterParamsOptionNumber specifies the number of
         the DHCP option to filter on."
    REFERENCE
        "RFC 2132, RFC 3315, RFC 3633"
    DEFVAL { -1 }
    ::= { tDhcpFilterParamsEntry 4 }

tDhcpFilterParamsOptionMatch OBJECT-TYPE
    SYNTAX      TDhcpFilterMatch
    MAX-ACCESS  read-create
    STATUS      current
    DESCRIPTION
        "The value of tDhcpFilterParamsOptionMatch specifies the criteria that
         the DHCP option must match to trigger this filter entry.

         The value present(1) specifies that the DHCP option must be present,
         the value absent(2) specifies that the DHCP option must be absent. In
         these cases tDhcpFilterParamsOptionValue will be reset to an empty
         string.

         A value string(3), string-exact(4), string-invert(5),
         string-exact-invert(6), hex(7), hex-exact(8), hex-invert(9) or
         hex-exact-invert(10) requires an octet string to be present in
         tDhcpFilterParamsOptionValue to match against.
         "
    DEFVAL { present }
    ::= { tDhcpFilterParamsEntry 5 }

tDhcpFilterParamsAction OBJECT-TYPE
    SYNTAX      TDhcpFilterAction
    MAX-ACCESS  read-create
    STATUS      current
    DESCRIPTION
        "The action to take for DHCP host creation requests that match this
         filter entry.
         The value none(1) specifies normal host creation behaviour, the value
         bypass-host-creation(2) specifies to bypass host creation, the value
         drop(3) specifies to drop the DHCP message."
    DEFVAL { none }
    ::= { tDhcpFilterParamsEntry 6 }

tDhcpFilterParamsOptionValue OBJECT-TYPE
    SYNTAX      OCTET STRING (SIZE (0..127))
    MAX-ACCESS  read-create
    STATUS      current
    DESCRIPTION
        "The value of the object tDhcpFilterParamsOptionValue specifies
         the matching pattern for the filtered DHCP option.

         This object is mandatory at creation time. A zero length value is only
         allowed when the value of tDhcpFilterParamsOptionMatch is present(1)
         or absent(2)."
    ::= { tDhcpFilterParamsEntry 7 }

-- ----------------------
-- tMacFilterNameTable
-- ----------------------

tMacFilterNameTableLastChgd OBJECT-TYPE
    SYNTAX      TimeStamp
    MAX-ACCESS  read-only
    STATUS      current
    DESCRIPTION
        "The value of tMacFilterNameTableLastChgd indicates the
         sysUpTime at the time of the last modification
         of tMacFilterNameTable.

         If no changes were made to the entry since the last
         re-initialization of the local network management subsystem,
         then this object contains a zero value."
    ::= { tFilterObjects 25 }

tMacFilterNameTable OBJECT-TYPE
    SYNTAX      SEQUENCE OF TMacFilterNameEntry
    MAX-ACCESS  not-accessible
    STATUS      current
    DESCRIPTION
        "A table that contains MAC filter name information. Entries
         are created automatically by the system
         when tMacFilterName object is set for the MAC filter."
    ::= { tFilterObjects 26 }

tMacFilterNameEntry OBJECT-TYPE
    SYNTAX      TMacFilterNameEntry
    MAX-ACCESS  not-accessible
    STATUS      current
    DESCRIPTION
        "Basic information about a specific MAC filter name."
    INDEX           { tMacFilterName }
    ::= { tMacFilterNameTable 1 }

TMacFilterNameEntry ::=
    SEQUENCE {
        tMacFilterNameId                   TAnyFilterID,
        tMacFilterNameRowStatus            RowStatus,
        tMacFilterNameLastChanged          TimeStamp
    }

tMacFilterNameId OBJECT-TYPE
    SYNTAX      TAnyFilterID
    MAX-ACCESS  read-only
    STATUS      current
    DESCRIPTION
        "The value of the object tMacFilterNameId indicates the filter
         name associated with this MAC filter."
    ::= { tMacFilterNameEntry 1 }

tMacFilterNameRowStatus OBJECT-TYPE
    SYNTAX      RowStatus
    MAX-ACCESS  read-only
    STATUS      current
    DESCRIPTION
        "This value of the object tMacFilterNameRowStatus indicates the
         status of this row."
    ::= { tMacFilterNameEntry 2 }

tMacFilterNameLastChanged OBJECT-TYPE
    SYNTAX      TimeStamp
    MAX-ACCESS  read-only
    STATUS      current
    DESCRIPTION
        "The value of tMacFilterNameLastChanged indicates the sysUpTime at
         the time of the last modification of this entry.

         If no changes were made to the entry since the last
         re-initialization of the local network management
         subsystem, then this object contains a zero value."
    ::= { tMacFilterNameEntry 3 }

-- ----------------------
-- tIpFilterNameTable
-- ----------------------

tIpFilterNameTableLastChgd OBJECT-TYPE
    SYNTAX      TimeStamp
    MAX-ACCESS  read-only
    STATUS      current
    DESCRIPTION
        "The value of tIpFilterNameTableLastChgd indicates the
         sysUpTime at the time of the last modification
         of tIpFilterNameTable.

         If no changes were made to the entry since the last
         re-initialization of the local network management subsystem,
         then this object contains a zero value."
    ::= { tFilterObjects 27 }

tIpFilterNameTable OBJECT-TYPE
    SYNTAX      SEQUENCE OF TIpFilterNameEntry
    MAX-ACCESS  not-accessible
    STATUS       current
    DESCRIPTION
        "A table that contains IP filter name information. Entries
         are created automatically by the system
         when tIpFilterName object is set for the IP filter."
    ::= { tFilterObjects 28 }

tIpFilterNameEntry OBJECT-TYPE
    SYNTAX      TIpFilterNameEntry
    MAX-ACCESS  not-accessible
    STATUS       current
    DESCRIPTION
        "Basic information about a specific IP filter name."
    INDEX           { tIpFilterName }
    ::= { tIpFilterNameTable 1 }

TIpFilterNameEntry ::=
    SEQUENCE {
        tIpFilterNameId                   TAnyFilterID,
        tIpFilterNameRowStatus            RowStatus,
        tIpFilterNameLastChanged          TimeStamp
    }

tIpFilterNameId OBJECT-TYPE
    SYNTAX      TAnyFilterID
    MAX-ACCESS  read-only
    STATUS      current
    DESCRIPTION
        "The value of the object tIpFilterNameId indicates the filter
         name associated with this IP filter."
    ::= { tIpFilterNameEntry 1 }

tIpFilterNameRowStatus OBJECT-TYPE
    SYNTAX      RowStatus
    MAX-ACCESS  read-only
    STATUS      current
    DESCRIPTION
        "This value of the object tIpFilterNameRowStatus indicates the
         status of this row."
    ::= { tIpFilterNameEntry 2 }

tIpFilterNameLastChanged OBJECT-TYPE
    SYNTAX      TimeStamp
    MAX-ACCESS  read-only
    STATUS      current
    DESCRIPTION
        "The value of tIpFilterNameLastChanged indicates the sysUpTime at
         the time of the last modification of this entry.

         If no changes were made to the entry since the last
         re-initialization of the local network management
         subsystem, then this object contains a zero value."
    ::= { tIpFilterNameEntry 3 }

-- ----------------------
-- tIpv6FilterNameTable
-- ----------------------

tIpv6FilterNameTableLastChgd OBJECT-TYPE
    SYNTAX      TimeStamp
    MAX-ACCESS  read-only
    STATUS      current
    DESCRIPTION
        "The value of tIpv6FilterNameTableLastChgd indicates the
         sysUpTime at the time of the last modification
         of tIpv6FilterNameTable.

         If no changes were made to the entry since the last
         re-initialization of the local network management subsystem,
         then this object contains a zero value."
    ::= { tFilterObjects 29 }

tIpv6FilterNameTable OBJECT-TYPE
    SYNTAX      SEQUENCE OF TIpv6FilterNameEntry
    MAX-ACCESS  not-accessible
    STATUS      current
    DESCRIPTION
        "A table that contains IPv6 filter name information. Entries
         are created automatically by the system
         when tIpv6FilterName object is set for the IPv6 filter."
    ::= { tFilterObjects 30 }

tIpv6FilterNameEntry OBJECT-TYPE
    SYNTAX      TIpv6FilterNameEntry
    MAX-ACCESS  not-accessible
    STATUS      current
    DESCRIPTION
        "Basic information about a specific IPv6 filter name."
    INDEX           { tIpv6FilterName }
    ::= { tIpv6FilterNameTable 1 }

TIpv6FilterNameEntry ::=
    SEQUENCE {
        tIpv6FilterNameId                   TAnyFilterID,
        tIpv6FilterNameRowStatus            RowStatus,
        tIpv6FilterNameLastChanged          TimeStamp
    }

tIpv6FilterNameId OBJECT-TYPE
    SYNTAX      TAnyFilterID
    MAX-ACCESS  read-only
    STATUS      current
    DESCRIPTION
        "The value of the object tIpv6FilterNameId indicates the filter
         name associated with this IPv6 filter."
    ::= { tIpv6FilterNameEntry 1 }

tIpv6FilterNameRowStatus OBJECT-TYPE
    SYNTAX      RowStatus
    MAX-ACCESS  read-only
    STATUS      current
    DESCRIPTION
        "This value of the object tIpv6FilterNameRowStatus indicates the
         status of this row."
    ::= { tIpv6FilterNameEntry 2 }

tIpv6FilterNameLastChanged OBJECT-TYPE
    SYNTAX      TimeStamp
    MAX-ACCESS  read-only
    STATUS     current
    DESCRIPTION
        "The value of tIpv6FilterNameLastChanged indicates the sysUpTime at
         the time of the last modification of this entry.

         If no changes were made to the entry since the last
         re-initialization of the local network management
         subsystem, then this object contains a zero value."
    ::= { tIpv6FilterNameEntry 3 }

-- ------------------
--  tFilterLiObjects
-- ------------------

tFilterLiObjects  OBJECT IDENTIFIER ::= { tFilterObjects 31 }

-- ----------------------
--  tLiReservedBlockTable
-- ----------------------

tLiReservedBlockTableLastChanged OBJECT-TYPE
    SYNTAX      TimeStamp
    MAX-ACCESS  read-only
    STATUS      current
    DESCRIPTION
        "The object tLiReservedBlockTableLastChanged indicates the
         sysUpTime at the time of the last modification
         of tLiReservedBlockTable.

         If no changes were made to the entry since the last
         re-initialization of the local network management subsystem,
         then this object contains a zero value."
    ::= { tFilterLiObjects 1 }

tLiReservedBlockTable OBJECT-TYPE
    SYNTAX      SEQUENCE OF TLiReservedBlockEntry
    MAX-ACCESS  not-accessible
    STATUS      current
    DESCRIPTION
        "The table tLiReservedBlockTable describes LI reserved blocks.
         In this release this table can have at most one entry."
    ::= { tFilterLiObjects 2 }

tLiReservedBlockEntry OBJECT-TYPE
    SYNTAX      TLiReservedBlockEntry
    MAX-ACCESS  not-accessible
    STATUS      current
    DESCRIPTION
        "Information about an LI reserved block. This block can be associated
         with one or more filters to reserve a number of entries in those
         filters for LI."
    INDEX { tLiReservedBlockName }
    ::= { tLiReservedBlockTable 1 }

TLiReservedBlockEntry ::=
    SEQUENCE {
        tLiReservedBlockName            TNamedItem,
        tLiReservedBlockRowStatus       RowStatus,
        tLiReservedBlockLastChanged     TimeStamp,
        tLiReservedBlockDescription     TItemDescription,
        tLiReservedBlockStart           TEntryIdOrZero,
        tLiReservedBlockSize            TEntryIdOrZero
    }

tLiReservedBlockName OBJECT-TYPE
    SYNTAX      TNamedItem
    MAX-ACCESS  not-accessible
    STATUS      current
    DESCRIPTION
        "The object tLiReservedBlockName uniquely identifies
         an LI reserved block."
    ::= { tLiReservedBlockEntry 1 }

tLiReservedBlockRowStatus OBJECT-TYPE
    SYNTAX      RowStatus
    MAX-ACCESS  read-create
    STATUS      current
    DESCRIPTION
        "The object tLiReservedBlockRowStatus specifies the
         status of this row."
    ::= { tLiReservedBlockEntry 2 }

tLiReservedBlockLastChanged OBJECT-TYPE
    SYNTAX      TimeStamp
    MAX-ACCESS  read-only
    STATUS      current
    DESCRIPTION
        "The object tLiReservedBlockLastChanged indicates the
         sysUpTime at the time of the last modification of this entry.

         If no changes were made to the entry since the last
         re-initialization of the local network management subsystem,
         then this object contains a zero value."
    ::= { tLiReservedBlockEntry 3 }

tLiReservedBlockDescription OBJECT-TYPE
    SYNTAX      TItemDescription
    MAX-ACCESS  read-create
    STATUS      current
    DESCRIPTION
        "The object tLiReservedBlockDescription specifies a description
         for this LI reserved block."
    DEFVAL { ''H }
    ::= { tLiReservedBlockEntry 4 }

tLiReservedBlockStart OBJECT-TYPE
    SYNTAX      TEntryIdOrZero
    MAX-ACCESS  read-create
    STATUS      current
    DESCRIPTION
        "The object tLiReservedBlockStart specifies the starting entry of
         the LI reserved block.

         If set to '0' no block is reserved. In this case the value of the
         object tLiReservedBlockSize will be set to '0' by the system."
    DEFVAL { 0 }
    ::= { tLiReservedBlockEntry 5 }

tLiReservedBlockSize OBJECT-TYPE
    SYNTAX      TEntryIdOrZero (0..32768)
    MAX-ACCESS  read-create
    STATUS      current
    DESCRIPTION
        "The object tLiReservedBlockSize specifies the size of the
         LI reserved block.

         If set to '0' no block is reserved. In this case the value of the
         object tLiReservedBlockStart will be set to '0' by the system.
         
         The maximum value of this object may be limited depending on
         hardware variants."
    DEFVAL { 0 }
    ::= { tLiReservedBlockEntry 6 }


-- --------------------------
-- tLiReservedBlockFltrTable
-- --------------------------

tLiReservedBlockFltrTableLastChg OBJECT-TYPE
    SYNTAX      TimeStamp
    MAX-ACCESS  read-only
    STATUS      current
    DESCRIPTION
        "The value of tLiReservedBlockFltrTableLastChg indicates the
         sysUpTime at the time of the last modification
         of tLiReservedBlockFltrTable.

         If no changes were made to the entry since the last
         re-initialization of the local network management subsystem,
         then this object contains a zero value."
    ::= { tFilterLiObjects 3 }

tLiReservedBlockFltrTable OBJECT-TYPE
    SYNTAX      SEQUENCE OF TLiReservedBlockFltrEntry
    MAX-ACCESS  not-accessible
    STATUS      current
    DESCRIPTION
        "The table tLiReservedBlockFltrTable contains associations between
         normal filters and LI block reservations."
    ::= { tFilterLiObjects 4 }

tLiReservedBlockFltrEntry OBJECT-TYPE
    SYNTAX      TLiReservedBlockFltrEntry
    MAX-ACCESS  not-accessible
    STATUS      current
    DESCRIPTION
        "An association of a normal filter with an LI block reservation.
         In this release MAC and IP/IPv6 filters are supported.

         Entries can be created and deleted via SNMP SET operations 
         to tLiReservedBlockFltrRowStatus."
    INDEX { tLiReservedBlockName,
            tLiReservedBlockFltrType,
            tLiReservedBlockFltrIdStart,
            tLiReservedBlockFltrIdEnd
    }
    ::= { tLiReservedBlockFltrTable 1 }

TLiReservedBlockFltrEntry ::=
    SEQUENCE {
        tLiReservedBlockFltrType         TFilterType,
        tLiReservedBlockFltrIdStart      TFilterID,
        tLiReservedBlockFltrIdEnd        TFilterID,
        tLiReservedBlockFltrRowStatus    RowStatus,
        tLiReservedBlockFltrLastChanged  TimeStamp
    }

tLiReservedBlockFltrType OBJECT-TYPE
    SYNTAX      TFilterType
    MAX-ACCESS  not-accessible
    STATUS      current
    DESCRIPTION
        "The object tLiReservedBlockFltrType specifies the type of filter
         this LI block reservation applies to.

         In this release MAC and IP/IPv6 filters are supported:
             fltrtypeselIp     (1)             
             fltrtypeselMac    (2)
             fltrtypeselIpv6   (4)"
    ::= { tLiReservedBlockFltrEntry 1 }

tLiReservedBlockFltrIdStart OBJECT-TYPE
    SYNTAX      TFilterID
    MAX-ACCESS  not-accessible
    STATUS      current
    DESCRIPTION
        "The object tLiReservedBlockFltrIdStart specifies the ID of the
         first filter to apply an LI block reservation.

         If the value of the object tLiReservedBlockFltrType is equal to 1 or 4
         (IP or IPv6 filter) then the scope of any filter (defined by the value 
         of the object tIPFilterScope or tIPv6FilterScope) inside of the range
         defined by the values of the objects tLiReservedBlockFltrIdStart and 
         tLiReservedBlockFltrIdEnd must not be equal to embedded (3).

         In this release, tLiReservedBlockFltrIdStart must be equal to
         tLiReservedBlockFltrIdEnd."
    ::= { tLiReservedBlockFltrEntry 2 }

tLiReservedBlockFltrIdEnd OBJECT-TYPE
    SYNTAX      TFilterID
    MAX-ACCESS  not-accessible
    STATUS      current
    DESCRIPTION
        "The object tLiReservedBlockFltrIdEnd specifies the ID of the
         last filter to apply an LI block reservation.

         If the value of the object tLiReservedBlockFltrType is equal to 1 or 4
         (IP or IPv6 filter) then the scope of any filter (defined by the value 
         of the object tIPFilterScope or tIPv6FilterScope) inside of the range
         defined by the values of the objects tLiReservedBlockFltrIdStart and 
         tLiReservedBlockFltrIdEnd must not be equal to embedded (3).

         In this release, tLiReservedBlockFltrIdEnd must be equal to
         tLiReservedBlockFltrIdStart."
    ::= { tLiReservedBlockFltrEntry 3 }

tLiReservedBlockFltrRowStatus OBJECT-TYPE
    SYNTAX      RowStatus
    MAX-ACCESS  read-create
    STATUS      current
    DESCRIPTION
        "The object tLiReservedBlockFltrRowStatus specifies the
         status of this row."
    ::= { tLiReservedBlockFltrEntry 4 }

tLiReservedBlockFltrLastChanged OBJECT-TYPE
    SYNTAX      TimeStamp
    MAX-ACCESS  read-only
    STATUS      current
    DESCRIPTION
        "The object tLiReservedBlockFltrLastChanged indicates the
         sysUpTime at the time of the last modification of this entry.

         If no changes were made to the entry since the last
         re-initialization of the local network management subsystem,
         then this object contains a zero value."
    ::= { tLiReservedBlockFltrEntry 5 }

-- --------------------
--  tLiFilterTable
-- --------------------

tLiFilterTableLastChanged OBJECT-TYPE
    SYNTAX      TimeStamp
    MAX-ACCESS  read-only
    STATUS      current
    DESCRIPTION
        "The object tLiFilterTableLastChanged indicates the
        sysUpTime at the time of the last modification
        of tLiFilterTable.

        If no changes were made to the entry since the last
        re-initialization of the local network management subsystem,
        then this object contains a zero value."
    ::= { tFilterLiObjects 5 }

tLiFilterTable OBJECT-TYPE
    SYNTAX      SEQUENCE OF TLiFilterEntry
    MAX-ACCESS  not-accessible
    STATUS      current
    DESCRIPTION
        "The table tLiFilterTable contains information about
         all LI filters.

         In this release MAC and IP/IPv6 filters are supported."
    ::= { tFilterLiObjects 6 }

tLiFilterEntry OBJECT-TYPE
    SYNTAX      TLiFilterEntry
    MAX-ACCESS  not-accessible
    STATUS      current
    DESCRIPTION
        "Each entry represents an LI filter. In this release MAC and IP/IPv6
         filters are supported.

         Entries can be created and deleted via SNMP SET operations 
         to tLiFilterRowStatus."
    INDEX { tLiFilterType, 
            tLiFilterName 
    }
    ::= { tLiFilterTable 1 }

TLiFilterEntry ::=
    SEQUENCE {
        tLiFilterType                 TFilterType,
        tLiFilterName                 TNamedItem,
        tLiFilterRowStatus            RowStatus,
        tLiFilterLastChanged          TimeStamp,
        tLiFilterDescription          TItemDescription
    }

tLiFilterType OBJECT-TYPE
    SYNTAX      TFilterType
    MAX-ACCESS  not-accessible
    STATUS      current
    DESCRIPTION
        "The object tLiFilterType specifies the type of this LI filter.

         In this release MAC and IP/IPv6 filters are supported."
    ::= { tLiFilterEntry 1 }

tLiFilterName OBJECT-TYPE
    SYNTAX      TNamedItem
    MAX-ACCESS  not-accessible
    STATUS      current
    DESCRIPTION
        "The object tLiFilterName indicates the unique name of this
         LI Filter."
    ::= { tLiFilterEntry 2 }

tLiFilterRowStatus OBJECT-TYPE
    SYNTAX      RowStatus
    MAX-ACCESS  read-create
    STATUS      current
    DESCRIPTION
        "The object tLiFilterRowStatus specifies the status of this row."
    ::= { tLiFilterEntry 3 }

tLiFilterLastChanged OBJECT-TYPE
    SYNTAX      TimeStamp
    MAX-ACCESS  read-only
    STATUS      current
    DESCRIPTION
        "The object tLiFilterLastChanged indicates the
         sysUpTime at the time of the last modification of this entry.

         If no changes were made to the entry since the last
         re-initialization of the local network management subsystem,
         then this object contains a zero value."
    ::= { tLiFilterEntry 4 }

tLiFilterDescription OBJECT-TYPE
    SYNTAX      TItemDescription
    MAX-ACCESS  read-create
    STATUS      current
    DESCRIPTION
        "The object tLiFilterDescription specifies a description for this
         LI filter."
    DEFVAL { ''H}
    ::= { tLiFilterEntry 5 }

-- --------------------------
--  tLiFilterAssociationTable
-- --------------------------

tLiFilterAssociationTableLastChg OBJECT-TYPE
    SYNTAX      TimeStamp
    MAX-ACCESS  read-only
    STATUS      current
    DESCRIPTION
        "The object tLiFilterAssociationTableLastChg indicates the
        sysUpTime at the time of the last modification
        of tLiFilterAssociationTable.

        If no changes were made to the entry since the last
        re-initialization of the local network management subsystem,
        then this object contains a zero value."
    ::= { tFilterLiObjects 7 }

tLiFilterAssociationTable OBJECT-TYPE
    SYNTAX      SEQUENCE OF TLiFilterAssociationEntry
    MAX-ACCESS  not-accessible
    STATUS      current
    DESCRIPTION
        "The table tLiFilterAssociationTable contains information about
         the associations between LI filters and normal filters."
    ::= { tFilterLiObjects 8 }

tLiFilterAssociationEntry OBJECT-TYPE
    SYNTAX      TLiFilterAssociationEntry
    MAX-ACCESS  not-accessible
    STATUS      current
    DESCRIPTION
        "An association between an LI filter and a normal filter."
    INDEX { tLiFilterType, tLiFilterName, tLiFilterAssociationFltrId }
    ::= { tLiFilterAssociationTable 1 }

TLiFilterAssociationEntry ::=
    SEQUENCE {
        tLiFilterAssociationFltrId    TFilterID,
        tLiFilterAssociationRowStatus RowStatus,
        tLiFilterAssociationLastChg   TimeStamp
    }

tLiFilterAssociationFltrId OBJECT-TYPE
    SYNTAX      TFilterID
    MAX-ACCESS  not-accessible
    STATUS      current
    DESCRIPTION
        "The object tLiFilterAssociationFltrId indicates the id of the normal
         filter in the association described by this entry."
    ::= { tLiFilterAssociationEntry 1 }

tLiFilterAssociationRowStatus OBJECT-TYPE
    SYNTAX      RowStatus
    MAX-ACCESS  read-create
    STATUS      current
    DESCRIPTION
        "The object tLiFilterAssociationRowStatus specifies the status of
         this row."
    ::= { tLiFilterAssociationEntry 2 }

tLiFilterAssociationLastChg OBJECT-TYPE
    SYNTAX      TimeStamp
    MAX-ACCESS  read-only
    STATUS      current
    DESCRIPTION
        "The object tLiFilterAssociationLastChg indicates the
         sysUpTime at the time of the last modification of this entry.

         If no changes were made to the entry since the last
         re-initialization of the local network management subsystem,
         then this object contains a zero value."
     ::= { tLiFilterAssociationEntry 3 }

-- ------------------------
--  tLiMacFilterEntryTable
-- ------------------------

tLiMacFilterParamsTableLastChg OBJECT-TYPE
    SYNTAX      TimeStamp
    MAX-ACCESS  read-only
    STATUS      current
    DESCRIPTION
        "The object tLiMacFilterParamsTableLastChg indicates the
        sysUpTime at the time of the last modification
        of tLiMacFilterParamsTable.

        If no changes were made to the entry since the last
        re-initialization of the local network management subsystem,
        then this object contains a zero value."
    ::= { tFilterLiObjects 9 }

tLiMacFilterParamsTable OBJECT-TYPE
    SYNTAX      SEQUENCE OF TLiMacFilterParamsEntry
    MAX-ACCESS  not-accessible
    STATUS      current
    DESCRIPTION
        "The table tLiMacFilterParamsTable contains all
         LI MAC filter match entries for all LI MAC filters."
    ::= { tFilterLiObjects 10 }

tLiMacFilterParamsEntry OBJECT-TYPE
    SYNTAX      TLiMacFilterParamsEntry
    MAX-ACCESS  not-accessible
    STATUS      current
    DESCRIPTION
        "An LI MAC filter match entry."
    INDEX { tLiFilterType, tLiFilterName, tLiMacFilterParamsId }
    ::= { tLiMacFilterParamsTable 1 }

TLiMacFilterParamsEntry ::=
    SEQUENCE {
        tLiMacFilterParamsId              TEntryId,
        tLiMacFilterParamsRowStatus       RowStatus,
        tLiMacFilterParamsLastChanged     TimeStamp,
        tLiMacFilterParamsDescription     TItemDescription,
        tLiMacFilterParamsFrameType       TFrameType,
        tLiMacFilterParamsSrcMAC          MacAddress,
        tLiMacFilterParamsSrcMACMask      MacAddress,
        tLiMacFilterParamsDstMAC          MacAddress,
        tLiMacFilterParamsDstMACMask      MacAddress,
        tLiMacFilterParamsIngrHitCount    Counter64,
        tLiMacFilterParamsEgrHitCount     Counter64,
        tLiMacFilterParamsIngrHitBytes    Counter64,
        tLiMacFilterParamsEgrHitBytes     Counter64
    }

tLiMacFilterParamsId OBJECT-TYPE
    SYNTAX      TEntryId
    MAX-ACCESS  not-accessible
    STATUS      current
    DESCRIPTION
        "The object tLiMacFilterParamsId indicates the secondary index for
         this entry. Every LI MAC filter may have multiple match entries,
         therefore every LI MAC filter match entry is identified by
         the tLiFilterName and tLiMacFilterParamsId."
    ::= { tLiMacFilterParamsEntry 1 }

tLiMacFilterParamsRowStatus OBJECT-TYPE
    SYNTAX      RowStatus
    MAX-ACCESS  read-create
    STATUS      current
    DESCRIPTION
        "The object tLiMacFilterParamsRowStatus specifies the status
         of this row."
    ::= { tLiMacFilterParamsEntry 2 }

tLiMacFilterParamsLastChanged OBJECT-TYPE
    SYNTAX      TimeStamp
    MAX-ACCESS  read-only
    STATUS      current
    DESCRIPTION
        "The object tLiMacFilterParamsLastChanged indicates the
         sysUpTime at the time of the last modification of this entry.

         If no changes were made to the entry since the last
         re-initialization of the local network management subsystem,
         then this object contains a zero value."
    ::= { tLiMacFilterParamsEntry 3 }

tLiMacFilterParamsDescription OBJECT-TYPE
    SYNTAX      TItemDescription
    MAX-ACCESS  read-create
    STATUS      current
    DESCRIPTION
        "The object tLiMacFilterParamsDescription specifies a description
         for this entry."
    DEFVAL { ''H}
    ::= { tLiMacFilterParamsEntry 4 }

tLiMacFilterParamsFrameType OBJECT-TYPE
    SYNTAX      TFrameType
    MAX-ACCESS  read-create
    STATUS      current
    DESCRIPTION
        "The object tLiMacFilterParamsFrameType specifies the type of
         mac frame for which we are defining this match criterion."
    DEFVAL { e802dot3 }
    ::= { tLiMacFilterParamsEntry 5 }

tLiMacFilterParamsSrcMAC OBJECT-TYPE
    SYNTAX      MacAddress
    MAX-ACCESS  read-create
    STATUS      current
    DESCRIPTION
        "The object tLiMacFilterParamsSrcMAC specifies the source MAC
         address to match for this LI MAC filter entry."
    DEFVAL { '000000000000'H }
    ::= { tLiMacFilterParamsEntry 6 }

tLiMacFilterParamsSrcMACMask OBJECT-TYPE
    SYNTAX      MacAddress
    MAX-ACCESS  read-create
    STATUS      current
    DESCRIPTION
        "The object tLiMacFilterParamsSrcMACMask specifies
         the source MAC mask value for this LI MAC filter match entry.
         The mask is ANDed with the MAC to match tLiMacFilterParamsSrcMAC.
         A cleared bit means ignore this bit, do not match. A set bit means
         match this bit with tLiMacFilterParamsSrcMAC.
         Use the value 00-00-00-00-00-00 to disable this filter criterion.
         If set to all zero, the value of tLiMacFilterParamsSrcMAC will
         be set to all zero by the system, and any attempt to change this
         value will be ignored."
    DEFVAL { '000000000000'H }
    ::= { tLiMacFilterParamsEntry 7 }

tLiMacFilterParamsDstMAC OBJECT-TYPE
    SYNTAX      MacAddress
    MAX-ACCESS  read-create
    STATUS      current
    DESCRIPTION
        "The object tLiMacFilterParamsDstMAC specifies the destination MAC
         to match for this LI MAC filter entry."
    DEFVAL { '000000000000'H }
    ::= { tLiMacFilterParamsEntry 8 }

tLiMacFilterParamsDstMACMask OBJECT-TYPE
    SYNTAX      MacAddress
    MAX-ACCESS  read-create
    STATUS      current
    DESCRIPTION
        "The object tLiMacFilterParamsDstMACMask specifies the
         destination MAC mask value for this LI MAC filter match entry.
         The mask is ANDed with the MAC to match tLiMacFilterParamsDstMAC.
         A cleared bit means ignore this bit, do not match. A set bit means
         match this bit with tLiMacFilterParamsDstMAC.
         Use the value 00-00-00-00-00-00 to disable this filter criteria.
         If set to all zero, the value of tLiMacFilterParamsDstMAC will
         be set to all zero by the system, and any attempt to change this
         value will be ignored."
    DEFVAL { '000000000000'H }
    ::= { tLiMacFilterParamsEntry 9 }

tLiMacFilterParamsIngrHitCount OBJECT-TYPE
    SYNTAX      Counter64
    MAX-ACCESS  read-only
    STATUS      current
    DESCRIPTION
        "The object tLiMacFilterParamsIngrHitCount indicates the number of
         times an ingress packet matched this entry."
    ::= { tLiMacFilterParamsEntry 10 }

tLiMacFilterParamsEgrHitCount OBJECT-TYPE
    SYNTAX      Counter64
    MAX-ACCESS  read-only
    STATUS      current
    DESCRIPTION
        "This object tLiMacFilterParamsEgrHitCount indicates the number of
         times an egress packet matched this entry."
    ::= { tLiMacFilterParamsEntry 11 }

tLiMacFilterParamsIngrHitBytes OBJECT-TYPE
    SYNTAX      Counter64
    MAX-ACCESS  read-only
    STATUS      current
    DESCRIPTION
        "The value of tLiMacFilterParamsIngrHitBytes indicates the number
         of bytes of all ingress packets that matched this entry."
    ::= { tLiMacFilterParamsEntry 12 }

tLiMacFilterParamsEgrHitBytes OBJECT-TYPE
    SYNTAX      Counter64
    MAX-ACCESS  read-only
    STATUS      current
    DESCRIPTION
        "The value of tLiMacFilterParamsEgrHitBytes indicates the number
         of bytes of all egress packets that matched this entry."
    ::= { tLiMacFilterParamsEntry 13 }
      
-- ------------------------
--  tLiIpFilterParamsTable
-- ------------------------
  
tLiIpFilterParamsTableLastChg OBJECT-TYPE
    SYNTAX      TimeStamp
    MAX-ACCESS  read-only
    STATUS      current
    DESCRIPTION
        "The value of the object tLiIpFilterParamsTableLastChg 
         indicates the sysUpTime at the time of the last modification
         of tLiIpFilterParamsTable.
 
         If no changes were made to the table since the last
         re-initialization of the local network management subsystem,
         then this object contains a zero value."
    ::= { tFilterLiObjects 15 }    

tLiIpFilterParamsTable OBJECT-TYPE
    SYNTAX      SEQUENCE OF TLiIPFilterParamsEntry
    MAX-ACCESS  not-accessible
    STATUS      current
    DESCRIPTION
        "The table tLiIpFilterParamsTable contains information pertaining 
         to match entries of LI IP/IPv6 filters."
    ::= { tFilterLiObjects 16 }
      
tLiIpFilterParamsEntry OBJECT-TYPE
    SYNTAX      TLiIPFilterParamsEntry
    MAX-ACCESS  not-accessible
    STATUS      current
    DESCRIPTION
        "Each entry represents a configuration of an LI IP/IPv6 filter entry.
        
         Entries can be created and deleted via SNMP SET operations 
         to tLiIpFilterParamsRowStatus."
    INDEX { tLiFilterType, 
            tLiFilterName, 
            tLiIpFilterParamsId }
    ::= { tLiIpFilterParamsTable 1 }

TLiIPFilterParamsEntry ::=
    SEQUENCE {
        tLiIpFilterParamsId                 TEntryId,
        tLiIpFilterParamsLastChanged        TimeStamp,
        tLiIpFilterParamsRowStatus          RowStatus,
        tLiIpFilterParamsDescription        TItemDescription,
        tLiIpFilterParamsSrcIpAddrType      InetAddressType,
        tLiIpFilterParamsSrcIpAddr          InetAddress,
        tLiIpFilterParamsSrcIpFullMask      InetAddress,
        tLiIpFilterParamsDstIpAddrType      InetAddressType,
        tLiIpFilterParamsDstIpAddr          InetAddress,
        tLiIpFilterParamsDstIpFullMask      InetAddress,
        tLiIpFilterParamsProtocolNextHdr    TIpProtocol,
        tLiIpFilterParamsSrcPortValue1      TTcpUdpPort,
        tLiIpFilterParamsSrcPortValue2      TTcpUdpPort,
        tLiIpFilterParamsSrcPortOper        TOperator,
        tLiIpFilterParamsDstPortValue1      TTcpUdpPort,
        tLiIpFilterParamsDstPortValue2      TTcpUdpPort,
        tLiIpFilterParamsDstPortOper        TOperator
    }

tLiIpFilterParamsId OBJECT-TYPE
    SYNTAX      TEntryId
    MAX-ACCESS  not-accessible
    STATUS      current
    DESCRIPTION
        "The value of the object tLiIpFilterParamsId indicates the tertiary 
         index for tLiIpFilterParamsEntry. 
         
         Every LI IP filter may have multiple match entries 
         therefore every entry is identified by the values 
         of tLiFilterType, tLiFilterName and tLiIpFilterParamsId."
    ::= { tLiIpFilterParamsEntry 1 }

tLiIpFilterParamsLastChanged OBJECT-TYPE
    SYNTAX      TimeStamp
    MAX-ACCESS  read-only
    STATUS      current
    DESCRIPTION
        "The value of the object tLiIpFilterParamsLastChanged indicates 
         the sysUpTime at the time of the last modification of this entry.

         If no changes were made to the entry since the last
         re-initialization of the local network management subsystem,
         then this object contains a zero value."
    ::= { tLiIpFilterParamsEntry 2 }

tLiIpFilterParamsRowStatus OBJECT-TYPE
    SYNTAX      RowStatus
    MAX-ACCESS  read-create
    STATUS      current
    DESCRIPTION
        "The value of the object tLiIpFilterParamsRowStatus specifies 
         the status of this row in tLiIpFilterParamsTable."
    ::= { tLiIpFilterParamsEntry 3 }

tLiIpFilterParamsDescription OBJECT-TYPE
    SYNTAX      TItemDescription
    MAX-ACCESS  read-create
    STATUS      current
    DESCRIPTION
        "The value of the object tLiIpFilterParamsDescription specifies 
         the description for this LI IP filter entry."
    DEFVAL { ''H}
    ::= { tLiIpFilterParamsEntry 4 }

tLiIpFilterParamsSrcIpAddrType OBJECT-TYPE
    SYNTAX      InetAddressType 
    MAX-ACCESS  read-create
    STATUS      current
    DESCRIPTION
        "The value of the object tLiIpFilterParamsSrcIpAddrType specifies
         the context in which the values of the objects 
         tLiIpFilterParamsSrcIpAddr and tLiIpFilterParamsSrcIpFullMask 
         are interpreted.
        
         Only following values are supported:
            unknown(0)
            ipv4(1)
            ipv6(2)
         
         Furthermore the value must be consistent with the filter type given 
         by the value of the index object tLiFilterType.
         
         If the value of this object is set to 'unknown' then the values
         of the objects tLiIpFilterParamsSrcIpAddr and 
         tLiIpFilterParamsSrcIpFullMask are automatically set
         to their default values."
    DEFVAL { unknown }
    ::= { tLiIpFilterParamsEntry 5 }
      
tLiIpFilterParamsSrcIpAddr OBJECT-TYPE
    SYNTAX      InetAddress (SIZE (0|4|16))
    MAX-ACCESS  read-create
    STATUS      current
    DESCRIPTION
        "The value of the object tLiIpFilterParamsSrcIpAddr specifies 
         the source IP address to be matched by this LI IP filter entry.
         
         The value must be consistent with the IP version value of
         the associated tLiIpFilterParamsSrcIpAddrType object.
         
         If the value of the object tLiIpFilterParamsSrcIpAddrType is set
         to 'unknown' then the value of this object is automatically set 
         to the default value."
    DEFVAL { ''H }
    ::= { tLiIpFilterParamsEntry 6 }

tLiIpFilterParamsSrcIpFullMask OBJECT-TYPE
    SYNTAX      InetAddress (SIZE (0|4|16))
    MAX-ACCESS  read-create
    STATUS      current
    DESCRIPTION
        "The value of the object tLiIpFilterParamsSrcIpFullMask specifies 
         the IP mask value that is ANDed with the received source 
         IP address to match the value in tLiIpFilterParamsSrcIpAddr.

         The value must be consistent with the IP version value of
         the associated tLiIpFilterParamsSrcIpAddrType object 
         and must not be equal to zero. 
         
         If the value of the object tLiIpFilterParamsSrcIpAddrType is set
         to 'unknown' then the value of this object is automatically set 
         to the default value."
    DEFVAL { ''H }
    ::= { tLiIpFilterParamsEntry 7 }

  tLiIpFilterParamsDstIpAddrType OBJECT-TYPE
    SYNTAX      InetAddressType 
    MAX-ACCESS  read-create
    STATUS      current
    DESCRIPTION
        "The value of the object tLiIpFilterParamsDstIpAddrType specifies
         the context in which the values of the objects 
         tLiIpFilterParamsDstIpAddr and tLiIpFilterParamsDstIpFullMask 
         are interpreted.
         
         Only following values are supported:
            unknown(0)
            ipv4(1)
            ipv6(2)

         Furthermore the value must always be consistent with the filter type 
         given by the value of the index object tLiFilterType.
         
         If the value of this object is set to 'unknown' then the values
         of the objects tLiIpFilterParamsDstIpAddr and 
         tLiIpFilterParamsDstIpFullMask are automatically set
         to their default values."
    DEFVAL { unknown }
    ::= { tLiIpFilterParamsEntry 8 }
      
tLiIpFilterParamsDstIpAddr OBJECT-TYPE
    SYNTAX      InetAddress (SIZE (0|4|16))
    MAX-ACCESS  read-create
    STATUS      current
    DESCRIPTION
        "The value of the object tLiIpFilterParamsDstIpAddr specifies 
         the destination IP address to be matched by this LI IP filter entry.
         
         The value must be consistent with the IP version value of
         the associated tLiIpFilterParamsDstIpAddrType object.
         
         If the value of the object tLiIpFilterParamsDstIpAddrType is set
         to 'unknown' then the value of this object is automatically set 
         to the default value."
    DEFVAL { ''H }
    ::= { tLiIpFilterParamsEntry 9 }

tLiIpFilterParamsDstIpFullMask OBJECT-TYPE
    SYNTAX      InetAddress (SIZE (0|4|16))
    MAX-ACCESS  read-create
    STATUS      current
    DESCRIPTION
        "The value of the object tLiIpFilterParamsDstIpFullMask specifies 
         the IP mask value that is ANDed with the received destination 
         IP address to match the value in tLiIpFilterParamsDstIpAddr.

         The value must be consistent with the IP version value of
         the associated tLiIpFilterParamsDstIpAddrType object 
         and must not be equal to zero.
         
         If the value of the object tLiIpFilterParamsDstIpAddrType is set
         to 'unknown' then the value of this object is automatically set 
         to the default value."
    DEFVAL { ''H }
    ::= { tLiIpFilterParamsEntry 10 }

tLiIpFilterParamsProtocolNextHdr OBJECT-TYPE
    SYNTAX      TIpProtocol
    MAX-ACCESS  read-create
    STATUS      current
    DESCRIPTION
        "The value of the object tLiIpFilterParamsProtocolNextHdr specifies
         (depending on the filter type defined by the value of the object 
         tLiFilterType) the IP protocol / IPv6 next-header value to be matched 
         by this LI IP filter entry.
        
         The value must be set to -1 to disable the protocol / next-header 
         matching.
         
         Because the match criteria only pertains to the last next-header, 
         the following values are not accepted as IPv6 next-header values: 
         0, 43, 44, 50, 51, and 60."
    DEFVAL { -1 }
    ::= { tLiIpFilterParamsEntry 11 }
    
tLiIpFilterParamsSrcPortValue1 OBJECT-TYPE
    SYNTAX      TTcpUdpPort
    MAX-ACCESS  read-create
    STATUS      current
    DESCRIPTION
        "The value of the object tLiIpFilterParamsSrcPortValue1 specifies 
         the TCP/UDP source port value1. It is used as per the description 
         of tLiIpFilterParamsSrcPortOper."
    DEFVAL { 0 }
    ::= { tLiIpFilterParamsEntry 12 }

tLiIpFilterParamsSrcPortValue2 OBJECT-TYPE
    SYNTAX      TTcpUdpPort
    MAX-ACCESS  read-create
    STATUS      current
    DESCRIPTION
        "The value of the object tLiIpFilterParamsSrcPortValue2 specifies 
         the TCP/UDP source port value2. It is used as per the description 
         of tLiIpFilterParamsSrcPortOper."
    DEFVAL { 0 }
    ::= { tLiIpFilterParamsEntry 13 }

tLiIpFilterParamsSrcPortOper OBJECT-TYPE
    SYNTAX      TOperator
    MAX-ACCESS  read-create
    STATUS      current
    DESCRIPTION
        "The value of the object tLiIpFilterParamsSrcPortOper specifies
         the manner in which tLiIpFilterParamsSrcPortValue1 and 
         tLiIpFilterParamsSrcPortValue2 are to be used. The values of these 
         latter 2 objects and tLiIpFilterParamsSrcPortOper are used 
         as per the description of TTcpUdpPortOperator."
    DEFVAL { none }
    ::= { tLiIpFilterParamsEntry 14 }

tLiIpFilterParamsDstPortValue1 OBJECT-TYPE
    SYNTAX      TTcpUdpPort
    MAX-ACCESS  read-create
    STATUS      current
    DESCRIPTION
        "The value of the object tLiIpFilterParamsDstPortValue1 specifies 
         the TCP/UDP destination port value1. It is used as per the description 
         of tLiIpFilterParamsDstPortOper."
    DEFVAL { 0 }
    ::= { tLiIpFilterParamsEntry 15 }

tLiIpFilterParamsDstPortValue2 OBJECT-TYPE
    SYNTAX      TTcpUdpPort
    MAX-ACCESS  read-create
    STATUS      current
    DESCRIPTION
        "The value of the object tLiIpFilterParamsDstPortValue2 specifies 
         the TCP/UDP destination port value2. It is used as per the description 
         of tLiIpFilterParamsDstPortOper."
    DEFVAL { 0 }
    ::= { tLiIpFilterParamsEntry 16 }

tLiIpFilterParamsDstPortOper OBJECT-TYPE
    SYNTAX      TOperator
    MAX-ACCESS  read-create
    STATUS      current
    DESCRIPTION
        "The value of the object tLiIpFilterParamsDstPortOper specifies
         the manner in which tLiIpFilterParamsDstPortValue1 and 
         tLiIpFilterParamsDstPortValue2 are to be used. The values of these 
         latter 2 objects and tLiIpFilterParamsDstPortOper are used 
         as per the description in TTcpUdpPortOperator."
    DEFVAL { none }
    ::= { tLiIpFilterParamsEntry 17 }

-- ----------------------------
--  tLiIpFilterParamsInfoTable
-- ----------------------------

tLiIpFilterParamsInfoTable OBJECT-TYPE
    SYNTAX      SEQUENCE OF TLiIPFilterParamsInfoEntry
    MAX-ACCESS  not-accessible
    STATUS      current
    DESCRIPTION
        "The table tLiIpFilterParamsInfoTable contains read-only information
         pertaining to LI IP filter match entries of LI IP filters."
    ::= { tFilterLiObjects 17 }

tLiIpFilterParamsInfoEntry OBJECT-TYPE
    SYNTAX      TLiIPFilterParamsInfoEntry
    MAX-ACCESS  not-accessible
    STATUS      current
    DESCRIPTION
        "This row complements the corresponding row in the 
         tLiIpFilterParamsTable with read-only operational info.
        
         Entries are created and deleted automatically by the system 
         when a corresponding entry in tLiIpFilterParamsTable is 
         created / deleted."
    AUGMENTS {tLiIpFilterParamsEntry}
    ::= { tLiIpFilterParamsInfoTable 1 }

TLiIPFilterParamsInfoEntry ::=
    SEQUENCE {
        tLiIpFltrParamsInfIngrHitCount       Counter64,
        tLiIpFltrParamsInfEgrHitCount        Counter64,
        tLiIpFltrParamsInfIngrHitBytes       Counter64,
        tLiIpFltrParamsInfEgrHitBytes        Counter64
    }

tLiIpFltrParamsInfIngrHitCount OBJECT-TYPE
    SYNTAX      Counter64
    MAX-ACCESS  read-only
    STATUS      current
    DESCRIPTION
        "The value of the object tLiIpFltrParamsInfIngrHitCount indicates 
         the number of times an ingress packet matched this entry."
    ::= { tLiIpFilterParamsInfoEntry 1 }

tLiIpFltrParamsInfEgrHitCount OBJECT-TYPE
    SYNTAX      Counter64
    MAX-ACCESS  read-only
    STATUS      current
    DESCRIPTION
        "The value of the object tLiIpFltrParamsInfEgrHitCount indicates 
         the number of times an egress packet matched this entry."
    ::= { tLiIpFilterParamsInfoEntry 2 }

tLiIpFltrParamsInfIngrHitBytes OBJECT-TYPE
    SYNTAX      Counter64
    MAX-ACCESS  read-only
    STATUS      current
    DESCRIPTION
        "The value of the object tLiIpFltrParamsInfIngrHitBytes indicates 
         the number of bytes of all ingress packets that matched this entry."
    ::= { tLiIpFilterParamsInfoEntry 3 }

tLiIpFltrParamsInfEgrHitBytes OBJECT-TYPE
    SYNTAX      Counter64
    MAX-ACCESS  read-only
    STATUS      current
    DESCRIPTION
        "The value of the object tLiIpFltrParamsInfEgrHitBytes indicates 
         the number of bytes of all egress packets that matched this entry."
    ::= { tLiIpFilterParamsInfoEntry 4 }
     
-- ------------------------
--  tFilterPrefixListTable
-- ------------------------

tFilterPrefixListTableLstChng OBJECT-TYPE
    SYNTAX      TimeStamp
    MAX-ACCESS  read-only
    STATUS      current
    DESCRIPTION
        "The object tFilterPrefixListTableLstChng indicates the
        sysUpTime at the time of the last modification
        of tFilterPrefixListTable.

        If no changes were made to the table since the last
        re-initialization of the local network management subsystem,
        this object contains the value zero."
    ::= {  tFilterObjects 32 }

tFilterPrefixListTable OBJECT-TYPE
    SYNTAX      SEQUENCE OF TFilterPrefixListEntry
    MAX-ACCESS  not-accessible
    STATUS      current
    DESCRIPTION
        "The table tFilterPrefixListTable contains an entry
         for each prefix list defined in the filter area."
    ::= { tFilterObjects 33 }

tFilterPrefixListEntry OBJECT-TYPE
    SYNTAX      TFilterPrefixListEntry
    MAX-ACCESS  not-accessible
    STATUS      current
    DESCRIPTION
        "An entry in the tFilterPrefixListTable."
    INDEX {tFilterPrefixListType,
           IMPLIED tFilterPrefixListName }
    ::= { tFilterPrefixListTable 1 }

TFilterPrefixListEntry ::=
    SEQUENCE {
        tFilterPrefixListType            TFltrPrefixListType,
        tFilterPrefixListName            TNamedItem,
        tFilterPrefixListRowStatus       RowStatus,
        tFilterPrefixListLastChanged     TimeStamp,
        tFilterPrefixListDescription     TItemDescription
    }

tFilterPrefixListType OBJECT-TYPE
    SYNTAX      TFltrPrefixListType
    MAX-ACCESS  not-accessible
    STATUS      current
    DESCRIPTION
        "The object tFilterPrefixListType specifies the type
         of prefix list for the prefix list tFilterPrefixListName."
    ::= { tFilterPrefixListEntry 1 }

tFilterPrefixListName OBJECT-TYPE
    SYNTAX      TNamedItem
    MAX-ACCESS  not-accessible
    STATUS      current
    DESCRIPTION
        "The object tFilterPrefixListName specifies the name
         given to this prefix list."
    ::= { tFilterPrefixListEntry 2 }

tFilterPrefixListRowStatus OBJECT-TYPE
    SYNTAX      RowStatus
    MAX-ACCESS  read-create
    STATUS      current
    DESCRIPTION
        "The object tFilterPrefixListRowStatus specifies the status
         of this row."
    ::= { tFilterPrefixListEntry 3 }

tFilterPrefixListLastChanged OBJECT-TYPE
    SYNTAX      TimeStamp
    MAX-ACCESS  read-only
    STATUS      current
    DESCRIPTION
        "The object tFilterPrefixListLastChanged indicates the
         sysUpTime at the time of the last modification of this row.

         If no changes were made to the row since the last
         re-initialization of the local network management subsystem,
         then this object contains the value zero."
    ::= { tFilterPrefixListEntry 4 }

tFilterPrefixListDescription OBJECT-TYPE
    SYNTAX      TItemDescription
    MAX-ACCESS  read-create
    STATUS      current
    DESCRIPTION
        "The object tFilterPrefixListDescription specifies a description
         for this row."
    DEFVAL { ''H}
    ::= { tFilterPrefixListEntry 5 }

-- ----------------------------
--  tFilterPrefixListEntryTable
-- ----------------------------

tFilterPrefixListEntryTblLstChg OBJECT-TYPE
    SYNTAX      TimeStamp
    MAX-ACCESS  read-only
    STATUS      current
    DESCRIPTION
        "The object tFilterPrefixListEntryTblLstChg indicates the
        sysUpTime at the time of the last modification
        of tFilterPrefixListEntryTable.

        If no changes were made to the table since the last
        re-initialization of the local network management subsystem,
        this object contains the value zero."
    ::= {  tFilterObjects 34 }

tFilterPrefixListEntryTable OBJECT-TYPE
    SYNTAX      SEQUENCE OF TFilterPrefixListEntryEntry
    MAX-ACCESS  not-accessible
    STATUS      current
    DESCRIPTION
        "The table tFilterPrefixListEntryTable contains information pertaining
         to explicitly created prefixes in any prefix list defined in the
         filter area."
    ::= { tFilterObjects 35 }

tFilterPrefixListEntryEntry OBJECT-TYPE
    SYNTAX      TFilterPrefixListEntryEntry
    MAX-ACCESS  not-accessible
    STATUS      current
    DESCRIPTION
        "An entry in the tFilterPrefixListEntryTable."
    INDEX {tFilterPrefixListType,
           tFilterPrefixListName,
           tFilterPrefixListEntryPrefixType,
           tFilterPrefixListEntryPrefix,
           tFilterPrefixListEntryPrefixLen}
    ::= { tFilterPrefixListEntryTable 1 }

TFilterPrefixListEntryEntry ::=
    SEQUENCE {
        tFilterPrefixListEntryPrefixType InetAddressType,
        tFilterPrefixListEntryPrefix     InetAddress,
        tFilterPrefixListEntryPrefixLen  InetAddressPrefixLength,
        tFilterPrefixListEntryRowStatus  RowStatus
    }

tFilterPrefixListEntryPrefixType OBJECT-TYPE
    SYNTAX      InetAddressType
    MAX-ACCESS  not-accessible
    STATUS      current
    DESCRIPTION
        "The object tFilterPrefixListEntryPrefixType specifies whether the
         prefix specified in tFilterPrefixListEntryPrefix is an IPv4 or IPv6
         prefix.

         The value of tFilterPrefixListEntryPrefixType must match the value
         of the object tFilterPrefixListType."
    ::= { tFilterPrefixListEntryEntry 1 }

tFilterPrefixListEntryPrefix OBJECT-TYPE
    SYNTAX      InetAddress (SIZE (4|16))
    MAX-ACCESS  not-accessible
    STATUS      current
    DESCRIPTION
        "The value of tFilterPrefixListEntryPrefix specifies
         the IP prefix of this prefix list entry."
    ::= { tFilterPrefixListEntryEntry 2 }

tFilterPrefixListEntryPrefixLen OBJECT-TYPE
    SYNTAX      InetAddressPrefixLength
    MAX-ACCESS  not-accessible
    STATUS      current
    DESCRIPTION
        "The value of tFilterPrefixListEntryPrefixLen specifies
         the IP prefix length of this prefix list entry."
    ::= { tFilterPrefixListEntryEntry 3 }

tFilterPrefixListEntryRowStatus OBJECT-TYPE
    SYNTAX      RowStatus
    MAX-ACCESS  read-create
    STATUS      current
    DESCRIPTION
        "The object tFilterPrefixListEntryRowStatus specifies the status
         of this row."
    ::= { tFilterPrefixListEntryEntry 4 }

-- ----------------------------
--  tFilterEmbeddedRefTable
-- ----------------------------
tFilterEmbeddedRefTableLstChg OBJECT-TYPE
    SYNTAX      TimeStamp
    MAX-ACCESS  read-only
    STATUS      current
    DESCRIPTION
        "The object tFilterEmbeddedRefTableLstChg indicates the
        sysUpTime at the time of the last modification
        of tFilterEmbeddedRefTable.

        If no changes were made to the table since the last
        re-initialization of the local network management subsystem,
        this object contains the value zero."
    ::= {  tFilterObjects 36 }

tFilterEmbeddedRefTable OBJECT-TYPE
    SYNTAX      SEQUENCE OF TFilterEmbeddedRefTableEntry
    MAX-ACCESS  not-accessible
    STATUS      current
    DESCRIPTION
        "The table tFilterEmbeddedRefTable contains an entry
         for each embedded filter inserted in a filter with scope other
         than 'embedded'."
    ::= { tFilterObjects 37 }

tFilterEmbeddedRefTableEntry OBJECT-TYPE
    SYNTAX      TFilterEmbeddedRefTableEntry
    MAX-ACCESS  not-accessible
    STATUS      current
    DESCRIPTION
        "An entry in the tFilterEmbeddedRefTable."
    INDEX {tFilterEmbeddedRefFilterType,
           tFilterEmbeddedRefInsertFltrId,
           tFilterEmbeddedRefEmbeddedFltrId,
           tFilterEmbeddedRefOffset}
    ::= { tFilterEmbeddedRefTable 1 }

TFilterEmbeddedRefTableEntry ::=
    SEQUENCE {
        tFilterEmbeddedRefFilterType     TFilterType,
        tFilterEmbeddedRefInsertFltrId   TFilterID,
        tFilterEmbeddedRefEmbeddedFltrId TFilterID,
        tFilterEmbeddedRefOffset         TFilterEmbedOffset,
        tFilterEmbeddedRefRowStatus      RowStatus,
        tFilterEmbeddedRefAdminState     TmnxEmbeddedFltrAdminState,
        tFilterEmbeddedRefOperState      TmnxEmbeddedFltrOperState,
        tFilterEmbeddedRefLastChanged    TimeStamp
    }

tFilterEmbeddedRefFilterType OBJECT-TYPE
    SYNTAX      TFilterType
    MAX-ACCESS  not-accessible
    STATUS      current
    DESCRIPTION
        "The object tFilterEmbeddedRefFilterType specifies the type of filter
         for the filters specified by tFilterEmbeddedRefEmbeddedFltrId and
         tFilterEmbeddedRefInsertFltrId."
    ::= { tFilterEmbeddedRefTableEntry 1 }

tFilterEmbeddedRefInsertFltrId OBJECT-TYPE
    SYNTAX      TFilterID
    MAX-ACCESS  not-accessible
    STATUS      current
    DESCRIPTION
        "The value of tFilterEmbeddedRefInsertFltrId specifies the filter
         where the filter specified by tFilterEmbeddedRefEmbeddedFltrId
         is to be inserted."
    ::= { tFilterEmbeddedRefTableEntry 2 }

tFilterEmbeddedRefEmbeddedFltrId OBJECT-TYPE
    SYNTAX      TFilterID
    MAX-ACCESS  not-accessible
    STATUS      current
    DESCRIPTION
        "The value of tFilterEmbeddedRefEmbeddedFltrId specifies
         the id of the filter to be inserted in the filter specified
         by tFilterEmbeddedRefInsertFltrId."
    ::= { tFilterEmbeddedRefTableEntry 3 }

tFilterEmbeddedRefOffset OBJECT-TYPE
    SYNTAX      TFilterEmbedOffset
    MAX-ACCESS  not-accessible
    STATUS      current
    DESCRIPTION
        "The value of tFilterEmbeddedRefOffset specifies the offset of
         inserted entries."
    ::= { tFilterEmbeddedRefTableEntry 4 }

tFilterEmbeddedRefRowStatus OBJECT-TYPE
    SYNTAX      RowStatus
    MAX-ACCESS  read-create
    STATUS      current
    DESCRIPTION
        "The object tFilterEmbeddedRefRowStatus specifies the status
         of this row."
    ::= { tFilterEmbeddedRefTableEntry 5 }

tFilterEmbeddedRefAdminState OBJECT-TYPE
    SYNTAX      TmnxEmbeddedFltrAdminState
    MAX-ACCESS  read-create
    STATUS      current
    DESCRIPTION
        "The value of tFilterEmbeddedRefAdminState specifies the administrative
         state of the embed request defined by this row.

         If an active embedding cannot be fulfilled due to dynamic events, this
         object will be set to 'inactive' automatically by the system. In those
         cases, the object tFilterEmbeddedRefOperState will indicate the failure
         reason."
    DEFVAL { active }
    ::= { tFilterEmbeddedRefTableEntry 6 }

tFilterEmbeddedRefOperState OBJECT-TYPE
    SYNTAX      TmnxEmbeddedFltrOperState
    MAX-ACCESS  read-only
    STATUS      current
    DESCRIPTION
        "The value of tFilterEmbeddedRefOperState indicates the operational
         state of the embed request defined by this row."
    ::= { tFilterEmbeddedRefTableEntry 7 }

tFilterEmbeddedRefLastChanged OBJECT-TYPE
    SYNTAX      TimeStamp
    MAX-ACCESS  read-only
    STATUS      current
    DESCRIPTION
        "The value of tFilterEmbeddedRefLastChanged indicates the sysUpTime
         at the time of last change to this row
         in tFilterEmbeddedRefTable."
    ::= { tFilterEmbeddedRefTableEntry 8 }

-- ------------------------
--  tFilterPortListTable
-- ------------------------

tFilterPortListTableLstChng OBJECT-TYPE
    SYNTAX      TimeStamp
    MAX-ACCESS  read-only
    STATUS      current
    DESCRIPTION
        "The object tFilterPortListTableLstChng indicates the
        sysUpTime at the time of the last modification
        of tFilterPortListTable.

        If no changes were made to the table since the last
        re-initialization of the local network management subsystem,
        this object contains the value zero."
    ::= {  tFilterObjects 38 }

tFilterPortListTable OBJECT-TYPE
    SYNTAX      SEQUENCE OF TFilterPortListEntry
    MAX-ACCESS  not-accessible
    STATUS      current
    DESCRIPTION
        "The table tFilterPortListTable contains an entry
         for each port list defined in the filter area."
    ::= { tFilterObjects 39 }

tFilterPortListEntry OBJECT-TYPE
    SYNTAX      TFilterPortListEntry
    MAX-ACCESS  not-accessible
    STATUS      current
    DESCRIPTION
        "An entry in the tFilterPortListTable."
    INDEX { IMPLIED tFilterPortListName }
    ::= { tFilterPortListTable 1 }

TFilterPortListEntry ::=
    SEQUENCE {
        tFilterPortListName            TNamedItem,
        tFilterPortListRowStatus       RowStatus,
        tFilterPortListLastChanged     TimeStamp,
        tFilterPortListDescription     TItemDescription
    }

tFilterPortListName OBJECT-TYPE
    SYNTAX      TNamedItem
    MAX-ACCESS  not-accessible
    STATUS      current
    DESCRIPTION
        "The object tFilterPortListName specifies the name
         given to this port list."
    ::= { tFilterPortListEntry 1 }

tFilterPortListRowStatus OBJECT-TYPE
    SYNTAX      RowStatus
    MAX-ACCESS  read-create
    STATUS      current
    DESCRIPTION
        "The object tFilterPortListRowStatus specifies the status
         of this row."
    ::= { tFilterPortListEntry 2 }

tFilterPortListLastChanged OBJECT-TYPE
    SYNTAX      TimeStamp
    MAX-ACCESS  read-only
    STATUS      current
    DESCRIPTION
        "The object tFilterPortListLastChanged indicates the
         sysUpTime at the time of the last modification of this row.

         If no changes were made to the row since the last
         re-initialization of the local network management subsystem,
         then this object contains the value zero."
    ::= { tFilterPortListEntry 3 }

tFilterPortListDescription OBJECT-TYPE
    SYNTAX      TItemDescription
    MAX-ACCESS  read-create
    STATUS      current
    DESCRIPTION
        "The object tFilterPortListDescription specifies a description
         for this row."
    DEFVAL { ''H}
    ::= { tFilterPortListEntry 4 }

-- ----------------------------
--  tFilterPortListEntryTable
-- ----------------------------

tFilterPortListEntryTblLstChg OBJECT-TYPE
    SYNTAX      TimeStamp
    MAX-ACCESS  read-only
    STATUS      current
    DESCRIPTION
        "The object tFilterPortListEntryTblLstChg indicates the
        sysUpTime at the time of the last modification
        of tFilterPortListEntryTable.

        If no changes were made to the table since the last
        re-initialization of the local network management subsystem,
        this object contains the value zero."
    ::= {  tFilterObjects 40 }

tFilterPortListEntryTable OBJECT-TYPE
    SYNTAX      SEQUENCE OF TFilterPortListEntryEntry
    MAX-ACCESS  not-accessible
    STATUS      current
    DESCRIPTION
        "The table tFilterPortListEntryTable contains an entry
         for each port defined in any port list
         defined in the filter area."
    ::= { tFilterObjects 41 }

tFilterPortListEntryEntry OBJECT-TYPE
    SYNTAX      TFilterPortListEntryEntry
    MAX-ACCESS  not-accessible
    STATUS      current
    DESCRIPTION
        "Specifies an entry in the tFilterPortListEntryTable.
         Two entries for the same port list must not overlap."
    INDEX { tFilterPortListName,
            tFilterPortListEntryPortLow,
            tFilterPortListEntryPortHigh }
    ::= { tFilterPortListEntryTable 1 }

TFilterPortListEntryEntry ::=
    SEQUENCE {
        tFilterPortListEntryPortLow   TTcpUdpPort,
        tFilterPortListEntryPortHigh  TTcpUdpPort,
        tFilterPortListEntryRowStatus RowStatus
    }

tFilterPortListEntryPortLow OBJECT-TYPE
    SYNTAX      TTcpUdpPort
    MAX-ACCESS  not-accessible
    STATUS      current
    DESCRIPTION
        "This object specifies the lower value for the TCP/UDP port range.
        A value assigned to this object must be less than or equal to the
        value assigned to the corresponding object
        tFilterPortListEntryPortHigh."
    ::= { tFilterPortListEntryEntry 1 }

tFilterPortListEntryPortHigh OBJECT-TYPE
    SYNTAX      TTcpUdpPort
    MAX-ACCESS  not-accessible
    STATUS      current
    DESCRIPTION
        "This object specifies the higher value for the TCP/UDP port range.
         A value assigned to this object must be greater than or equal to the
         value assigned to the corresponding object
         tFilterPortListEntryPortLow."
    ::= { tFilterPortListEntryEntry 2 }

tFilterPortListEntryRowStatus OBJECT-TYPE
    SYNTAX      RowStatus
    MAX-ACCESS  read-create
    STATUS      current
    DESCRIPTION
        "The object tFilterPortListEntryRowStatus specifies the status of this
         row."
    ::= { tFilterPortListEntryEntry 3 }


-- -------------------------
--  tPrefixListApplyPathTable
-- -------------------------

tFilterApplyPathTableLstChng OBJECT-TYPE
    SYNTAX      TimeStamp
    MAX-ACCESS  read-only
    STATUS      current
    DESCRIPTION
        "The object tFilterApplyPathTableLstChng indicates the
        sysUpTime at the time of the last modification
        of tFilterApplyPathTable.

        If no changes were made to the table since the last
        re-initialization of the local network management subsystem,
        this object contains the value zero."
    ::= {  tFilterObjects 42 }

tFilterApplyPathTable OBJECT-TYPE
    SYNTAX      SEQUENCE OF TFilterApplyPathEntry
    MAX-ACCESS  not-accessible
    STATUS      current
    DESCRIPTION
        "The table tFilterApplyPathTable contains an entry
         for each apply-path rule defined in a prefix-list."
    ::= { tFilterObjects 43 }

tFilterApplyPathEntry OBJECT-TYPE
    SYNTAX      TFilterApplyPathEntry
    MAX-ACCESS  not-accessible
    STATUS      current
    DESCRIPTION
        "An entry in the tFilterApplyPathTable describing an apply-path rule.
        
         If an address or prefix configured by the source specified by 
         tFilterApplyPathSource matches the conditions specified by 
         tFilterApplyPathMatch1 and tFilterApplyPathMatch2, a prefix is 
         inserted into the prefix-list where this apply-path rule refers to."
         
    INDEX { tFilterPrefixListType,
            tFilterPrefixListName,
            tFilterApplyPathSource,
            tFilterApplyPathIndex
          }            
    ::= { tFilterApplyPathTable 1}

TFilterApplyPathEntry ::=
    SEQUENCE {
        tFilterApplyPathSource         TmnxFilterApplyPathSource,
        tFilterApplyPathIndex          Unsigned32,
        tFilterApplyPathRowStatus      RowStatus,
        tFilterApplyPathLastChanged    TimeStamp,
        tFilterApplyPathMatch1         TRegularExpression,
        tFilterApplyPathMatch2         TRegularExpression
    }
    
tFilterApplyPathSource OBJECT-TYPE
    SYNTAX      TmnxFilterApplyPathSource
    MAX-ACCESS  not-accessible
    STATUS      current
    DESCRIPTION
        "The object tFilterApplyPathSource specifies the source of the prefixes 
         that will be generated by this apply-path rule."
    ::= { tFilterApplyPathEntry 1 }
    
tFilterApplyPathIndex OBJECT-TYPE
    SYNTAX      Unsigned32 (1..16)
    MAX-ACCESS  not-accessible
    STATUS      current
    DESCRIPTION
        "The object tFilterApplyPathIndex specifies an index for this row."
    ::= { tFilterApplyPathEntry 2 }
    
tFilterApplyPathRowStatus OBJECT-TYPE
    SYNTAX      RowStatus
    MAX-ACCESS  read-create
    STATUS      current
    DESCRIPTION
        "The object tFilterApplyPathRowStatus specifies the status of this
         row."
    ::= { tFilterApplyPathEntry 3 } 
    
tFilterApplyPathLastChanged OBJECT-TYPE
    SYNTAX      TimeStamp
    MAX-ACCESS  read-only
    STATUS      current
    DESCRIPTION
        "The object tFilterApplyPathLastChanged indicates the timestamp of
         the last change to this row."
    ::= { tFilterApplyPathEntry 4 } 
    
tFilterApplyPathMatch1 OBJECT-TYPE
    SYNTAX      TRegularExpression
    MAX-ACCESS  read-create
    STATUS      current
    DESCRIPTION
        "The object tFilterApplyPathMatch1 specifies a regular expression. 
         The usage of this object depends on the source specified 
         by tFilterApplyPathSource. 
         
         If tFilterApplyPathSource is 'bgp-peers', this object specifies a 
         match condition on the group-name of configured bgp peers."
    DEFVAL { ''H }
    ::= { tFilterApplyPathEntry 5 } 
    
tFilterApplyPathMatch2 OBJECT-TYPE
    SYNTAX      TRegularExpression
    MAX-ACCESS  read-create
    STATUS      current
    DESCRIPTION
        "The object tFilterApplyPathMatch2 specifies a regular expression. 
         The usage of this object depends on the source specified by 
         tFilterApplyPathSource. 
         
         If tFilterApplyPathSource is 'bgp-peers', this object specifies a 
         match condition on the ip or ipv6 address of configured bgp peers."
    DEFVAL { ''H }
    ::= { tFilterApplyPathEntry 6 } 
      
-- ----------------------------
--  tFilterEmbeddedRefInfoTable
-- ----------------------------

tFilterEmbeddedRefInfoTable OBJECT-TYPE
    SYNTAX      SEQUENCE OF TFilterEmbeddedRefInfoEntry
    MAX-ACCESS  not-accessible
    STATUS      current
    DESCRIPTION
        "The table tFilterEmbeddedRefInfoTable contains an entry
         for each embedded filter inserted in a filter with scope other
         than 'embedded'.
         
         This row complements the corresponding row in the 
         tFilterEmbeddedRefTable with read-only operational info."
    ::= { tFilterObjects 44 }

tFilterEmbeddedRefInfoEntry OBJECT-TYPE
    SYNTAX      TFilterEmbeddedRefInfoEntry
    MAX-ACCESS  not-accessible
    STATUS      current
    DESCRIPTION
        "An entry in the tFilterEmbeddedRefInfoTable."
    AUGMENTS {tFilterEmbeddedRefTableEntry}
    ::= { tFilterEmbeddedRefInfoTable 1 }

TFilterEmbeddedRefInfoEntry ::=
    SEQUENCE {
        tFltrEmbedRefInfEntryCnt         Unsigned32,
        tFltrEmbedRefInfEntryCntInsrtd   Unsigned32
    }

tFltrEmbedRefInfEntryCnt OBJECT-TYPE
    SYNTAX      Unsigned32
    MAX-ACCESS  read-only
    STATUS      current
    DESCRIPTION
        "The value of tFltrEmbedRefInfEntryCnt indicates how many entries
         are present in the embedded filter as specified in 
         tFilterEmbeddedRefEmbeddedFltrId."
    ::= { tFilterEmbeddedRefInfoEntry 1 }

tFltrEmbedRefInfEntryCntInsrtd OBJECT-TYPE
    SYNTAX      Unsigned32
    MAX-ACCESS  read-only
    STATUS      current
    DESCRIPTION
        "The value of tFltrEmbedRefInfEntryCntInsrtd indicates how many entries
         of the embedded filter (specified by tFilterEmbeddedRefEmbeddedFltrId)
         are actually placed inside the filter (specified by 
         tFilterEmbeddedRefInsertFltrId).
         
         If the object tFilterEmbeddedRefOperState is different from 'in-service'
         this object will always be zero.
         
         Else, the difference between the value of this object and the value of 
         tFltrEmbedRefInfEntryCnt indicates how many entries of the embedded
         filter were overwritten by local entries in the embedding filter."
    ::= { tFilterEmbeddedRefInfoEntry 2 }

-- ----------------------------
--  tFilterEmbeddedEntryRefInfoTable
-- ----------------------------

tFilterEmbeddedEntryRefInfoTable OBJECT-TYPE
    SYNTAX      SEQUENCE OF TFilterEmbeddedEntryRefInfoEntry
    MAX-ACCESS  not-accessible
    STATUS      current
    DESCRIPTION
        "The table tFilterEmbeddedEntryRefInfoTable contains an entry
         for each embedded filter entry inserted in a filter with scope other
         than 'embedded'."
    ::= { tFilterObjects 45 }

tFilterEmbeddedEntryRefInfoEntry OBJECT-TYPE
    SYNTAX      TFilterEmbeddedEntryRefInfoEntry
    MAX-ACCESS  not-accessible
    STATUS      current
    DESCRIPTION
        "An entry in the tFilterEmbeddedEntryRefInfoTable.
         Rows in the tFilterEmbeddedEntryRefInfoTable are created 
         by the SYSTEM when an embedded filter is inserted into a filter with
         scope other than 'embedded'.
         They are destroyed by the SYSTEM when an embedded filter 
         is removed from a filter with scope other than 'embedded'."
    INDEX {tFltrEmbedEntryFilterType,
           tFltrEmbedEntryInsertFltrId,
           tFltrEmbedEntryEmbeddedFltrId,
           tFltrEmbedEntryEmbeddedEntryId}
    ::= { tFilterEmbeddedEntryRefInfoTable 1 }

TFilterEmbeddedEntryRefInfoEntry ::=
    SEQUENCE {
        tFltrEmbedEntryFilterType        TFilterType,
        tFltrEmbedEntryInsertFltrId      TFilterID,
        tFltrEmbedEntryEmbeddedFltrId    TFilterID,
        tFltrEmbedEntryEmbeddedEntryId   TEntryId,
        tFltrEmbedEntryInsrtEntryId      TEmbedInsrtEntryId,
        tFltrEmbedEntryRefOperState      TmnxFltrEmbeddedEntryState
    }

tFltrEmbedEntryFilterType OBJECT-TYPE
    SYNTAX      TFilterType
    MAX-ACCESS  not-accessible
    STATUS      current
    DESCRIPTION
        "The object tFltrEmbedEntryFilterType specifies a filter type
         for the filters specified by tFltrEmbedEntryInsertFltrId
         and tFltrEmbedEntryEmbeddedFltrId."
    ::= { tFilterEmbeddedEntryRefInfoEntry 1 }

tFltrEmbedEntryInsertFltrId OBJECT-TYPE
    SYNTAX      TFilterID
    MAX-ACCESS  not-accessible
    STATUS      current
    DESCRIPTION
        "The value of tFltrEmbedEntryInsertFltrId specifies the filter
         where the filter specified by tFltrEmbedEntryEmbeddedFltrId
         is inserted."
    ::= { tFilterEmbeddedEntryRefInfoEntry 2 }

tFltrEmbedEntryEmbeddedFltrId OBJECT-TYPE
    SYNTAX      TFilterID
    MAX-ACCESS  not-accessible
    STATUS      current
    DESCRIPTION
        "The value of tFltrEmbedEntryEmbeddedFltrId specifies
         the ID of the filter inserted in the filter specified
         by tFltrEmbedEntryInsertFltrId."
    ::= { tFilterEmbeddedEntryRefInfoEntry 3 }

tFltrEmbedEntryEmbeddedEntryId OBJECT-TYPE
    SYNTAX      TEntryId
    MAX-ACCESS  not-accessible
    STATUS      current
    DESCRIPTION
        "The value of tFltrEmbedEntryEmbeddedEntryId specifies 
         the ID of the entry inside of the filter specified by 
         tFltrEmbedEntryEmbeddedFltrId."
    ::= { tFilterEmbeddedEntryRefInfoEntry 4 }

tFltrEmbedEntryInsrtEntryId OBJECT-TYPE
    SYNTAX      TEmbedInsrtEntryId
    MAX-ACCESS  read-only 
    STATUS      current
    DESCRIPTION
        "The value of tFltrEmbedEntryInsrtEntryId indicates which entry
         in the filter specified by tFltrEmbedEntryInsertFltrId corresponds 
         to the entry specified by tFltrEmbedEntryEmbeddedEntryId 
         in the filter specified by tFltrEmbedEntryEmbeddedFltrId."  
    ::= { tFilterEmbeddedEntryRefInfoEntry 5 }

tFltrEmbedEntryRefOperState OBJECT-TYPE
    SYNTAX      TmnxFltrEmbeddedEntryState
    MAX-ACCESS  read-only
    STATUS      current
    DESCRIPTION
        "The value of tFltrEmbedEntryRefOperState indicates the current status
         of the entry identified by tFltrEmbedEntryEmbeddedEntryId of 
         the filter identified by tFltrEmbedEntryEmbeddedFltrId that
         is embedded into the filter identified by tFltrEmbedEntryInsertFltrId."
    ::= { tFilterEmbeddedEntryRefInfoEntry 6 }

--
-- IPv6 Filter Entry parameters Extension Table
--

tIPv6FilterParamsExtTbleLstChgd OBJECT-TYPE
    SYNTAX      TimeStamp
    MAX-ACCESS  read-only
    STATUS      current
    DESCRIPTION
        "The value of tIPv6FilterParamsExtTbleLstChgd indicates the
         sysUpTime at the time of the last modification
         of tIPv6FilterParamsExtTable.

         If no changes were made to the entry since the last
         re-initialization of the local network management subsystem,
         then this object contains a zero value."
    ::= { tFilterObjects 46 }

tIPv6FilterParamsExtTable OBJECT-TYPE
    SYNTAX      SEQUENCE OF TIPv6FilterParamsExtEntry
    MAX-ACCESS  not-accessible
    STATUS      current
    DESCRIPTION
        " The table tIPv6FilterParamsExtTable contains, together with the
          table tIPv6FilterParamsTable info about every IPv6 filter entry in
          any of the configured IPv6 filters in the system.
       
          The table tIPv6FilterParamsExtTable was introduced due to the big size
          of the tIPv6FilterParamsTable."
    ::= { tFilterObjects 47 }

tIPv6FilterParamsExtEntry OBJECT-TYPE
    SYNTAX      TIPv6FilterParamsExtEntry
    MAX-ACCESS  not-accessible
    STATUS      current
    DESCRIPTION
        "Information about a particular IPv6 Filter entry.
         Every IPv6 Filter can have zero or more IPv6 Filter match entries.

         A filter entry with no match criteria set will match every
         packet, and the entry action will be taken.

         Rows are created/deleted by user.

         Additional match criteria can be found in tIPv6FilterParamsTable."
    AUGMENTS {tIPv6FilterParamsEntry}
    ::= { tIPv6FilterParamsExtTable 1 }

TIPv6FilterParamsExtEntry ::= SEQUENCE
    {
        tIPv6FilterParamsExtLastChanged  TimeStamp,
        tIPv6FilterParamsExtAhExtHdr     TItemMatch,
        tIPv6FilterParamsExtEspExtHdr    TItemMatch,
        tIPv6FilterParamsExtNatType      TmnxNatSubscriberType,
        tIPv6FilterParamsExtPktLenVal1   TFilterPacketLength,
        tIPv6FilterParamsExtPktLenVal2   TFilterPacketLength,
        tIPv6FilterParamsExtPktLenOper   TOperator,
        tIPv6FilterParamsExtHopLimitVal1 TFilterTTL,
        tIPv6FilterParamsExtHopLimitVal2 TFilterTTL,
        tIPv6FilterParamsExtHopLimitOper TOperator,
        tIPv6FilterParamsExtEgressPBR    TFilterEgressPBR,
        tIPv6FilterParamsExtEsi          TFilterEsi,
        tIPv6FilterParamsExtFwdEsiSvcId  TmnxServId,
        tIPv6FilterParamsExtFwdEsiVRtrId TmnxVRtrIDOrZero,
        tIPv6FilterParamsExtFwdEsiSFIp   InetAddressIPv6,
        tIPv6FilterParamsExtPbrDwnActOvr TFilterPbrDownActionOvr,
        tIPv6FilterParamsExtFwdEsiVasIf  InterfaceIndexOrZero,
        tIPv6FilterParamsExtStickyDst    Integer32,
        tIPv6FilterParamsExtHoldRemain   Integer32,
        tIPv6FilterParamsExtDownloadAct  TFilterDownloadedAction
   }

tIPv6FilterParamsExtLastChanged OBJECT-TYPE
    SYNTAX      TimeStamp
    MAX-ACCESS  read-only
    STATUS      current
    DESCRIPTION
        "The value of tIPv6FilterParamsExtLastChanged indicates the timestamp of
         last change to this row in tIPv6FilterParamsExtTable."
    ::= { tIPv6FilterParamsExtEntry 1 }

tIPv6FilterParamsExtAhExtHdr OBJECT-TYPE
    SYNTAX      TItemMatch
    MAX-ACCESS  read-create
    STATUS      current
    DESCRIPTION
        "If Enabled, matches the Authentication Extension Header (51) as per
         value of the object."
    DEFVAL { off }
    ::= { tIPv6FilterParamsExtEntry 2 }

tIPv6FilterParamsExtEspExtHdr OBJECT-TYPE
    SYNTAX      TItemMatch
    MAX-ACCESS  read-create
    STATUS      current
    DESCRIPTION
        "If Enabled, matches the Encapsulation Security Payload Extension Header
         (50) as per value of the object."
    DEFVAL { off }
    ::= { tIPv6FilterParamsExtEntry 3 }

tIPv6FilterParamsExtNatType OBJECT-TYPE
    SYNTAX TmnxNatSubscriberType {
        dsliteLsnSub  (3),
        nat64LsnSub   (4) 
    }
    MAX-ACCESS read-create
    STATUS current
    DESCRIPTION
        "This object specifies the NAT type to be used when the value of the
         corresponding tIPv6FilterParamsNatPolicyName object is nat.

         The value of tIPv6FilterParamsExtNatType is relevant only if the value
         of tIPv6FilterParamsAction is nat. Setting the value of
         tIPv6FilterParamsExtNatType to a non-default value is ignored by the
         system if the value of tIPv6FilterParamsAction is not nat.

         Furthermore, the value of tIPv6FilterParamsExtNatType is silently
         reset to the default value by the system if tIPv6FilterParamsAction is
         set to any value other than nat."
    DEFVAL { dsliteLsnSub }
    ::= { tIPv6FilterParamsExtEntry 4 }

tIPv6FilterParamsExtPktLenVal1 OBJECT-TYPE
    SYNTAX      TFilterPacketLength
    MAX-ACCESS  read-create
    STATUS      current
    DESCRIPTION
        "The value of the object tIPv6FilterParamsExtPktLenVal1 specifies
         the packet length value1 to be compared to the value of the Payload
         Length field of an IPv6 packet header that has hit this filter's entry.

         The way how the value of this object is used depends on the value
         of the object tIPv6FilterParamsExtPktLenOper.

         The value of this object is evaluated only if the value of the object
         tIPv6FilterParamsExtPktLenOper is other than 'none (0)'.

         If the value of tIPv6FilterParamsExtPktLenOper is 'range (2)' then
         the value of this object must be less than the value
         of tIPv6FilterParamsExtPktLenVal2.

         If the value of tIPv6FilterParamsExtPktLenOper is 'lt (3)' then
         the value of this object can be set in range 1..65535.

         If the value of tIPv6FilterParamsExtPktLenOper is 'gt (4)' then
         the value of this object can be set in range 0..65534.

         If both the values of the objects tIPv6FilterParamsExtPktLenOper and
         tIPv6FilterParamsExtPktLenVal1 need to be changed then it must be
         done in the same SET SNMP request.

         Note that the value of this object is silently cleared by the system
         if tIPv6FilterParamsAction is set to a value other than 'drop (1)'
         or
         if tIPv6FilterParamsExtPktLenOper is set to 'none (0)'
         or
         if tIPv6FilterParamsExtHopLimitOper is set to a value other
         than 'none (0)'."
    DEFVAL { 0 }
    ::= { tIPv6FilterParamsExtEntry 5 }

tIPv6FilterParamsExtPktLenVal2 OBJECT-TYPE
    SYNTAX      TFilterPacketLength
    MAX-ACCESS  read-create
    STATUS      current
    DESCRIPTION
        "The value of the object tIPv6FilterParamsExtPktLenVal2 specifies
         the packet length value2 to be compared to the value of the Payload
         Length field of an IPv6 packet header that has hit this filter's entry.

         The way how the value of this object is used depends on the value
         of the object tIPv6FilterParamsExtPktLenOper.

         The value of this object is evaluated only if the value of the object
         tIPv6FilterParamsExtPktLenOper is 'range (2)'.
         
         The value of this object must be greater than the value
         of tIPv6FilterParamsExtPktLenVal1.

         If both the values of the objects tIPv6FilterParamsExtPktLenOper and
         tIPv6FilterParamsExtPktLenVal2 need to be changed then it must be
         done in the same SET SNMP request.

         Note that the value of this object is silently cleared by the system
         if tIPv6FilterParamsAction is set to a value other than 'drop (1)'
         or
         if tIPv6FilterParamsExtPktLenOper is set to a value other
         than 'range (2)'
         or
         if tIPv6FilterParamsExtHopLimitOper is set to a value other
         than 'none (0)'."
    DEFVAL { 0 }
    ::= { tIPv6FilterParamsExtEntry 6 }

tIPv6FilterParamsExtPktLenOper OBJECT-TYPE
    SYNTAX      TOperator
    MAX-ACCESS  read-create
    STATUS      current
    DESCRIPTION
        "The value of the object tIPv6FilterParamsExtPktLenOper specifies
         the way how the values of the objects tIPv6FilterParamsExtPktLenVal1
         and tIPv6FilterParamsExtPktLenVal2 are used to form a condition that
         must be fulfilled in order to execute the action specified by the value
         of tIPv6FilterParamsAction. Otherwise the opposite action is executed.

         The value of this object can be set to a non-default value only if
         the value of the object tIPv6FilterParamsAction is 'drop (1)'.

         If the value of this object is being changed from the default value
         to any non-default value the values of the objects
         tIPv6FilterParamsExtPktLenVal1 and tIPv6FilterParamsExtPktLenVal2
         (if applicable) must be sent in the same SET SNMP request.

         If the value of this object is 'none (0)' than the values of
         the objects tIPv6FilterParamsExtPktLenVal1 and
         tIPv6FilterParamsExtPktLenVal2 are ignored and TRUE case action is
         always executed (see table below).

         If the value of this object is 'eq (1)' then the value of the Payload
         Length field of the IPv6 header of the packet that has matched this
         filter's entry must be equal to the value of the object
         tIPv6FilterParamsExtPktLenVal1 in order to execute the TRUE case action
         (see table below). Otherwise the FALSE case action is executed.
         The value of the object tIPv6FilterParamsExtPktLenVal2 is ignored.

         If the value of this object is 'range (2)' then the value of
         the Payload Length field of the IPv6 header of the packet that has
         matched this filter's entry must be greater than or equal to the value
         of the object tIPv6FilterParamsExtPktLenVal1 and less than or equal
         to the value of the object tIPv6FilterParamsExtPktLenVal2 in order
         to execute the TRUE case action (see table below). Otherwise the FALSE
         case action is executed.

         If the value of this object is 'lt (3)' then the value of the Payload
         Length field of the IPv6 header of the packet that has matched this
         filter's entry must be less than the value of the object
         tIPv6FilterParamsExtPktLenVal1 in order to execute the TRUE case action
         (see table below). Otherwise the FALSE case action is executed.
         The value of the object tIPv6FilterParamsExtPktLenVal2 is ignored.

         If the value of this object is 'gt (4)' then the value of the Payload
         Length field of the IPv6 header of the packet that has matched this
         filter's entry must be greater than the value of the object
         tIPv6FilterParamsExtPktLenVal1 in order to execute the TRUE case action
         (see table below). Otherwise the FALSE case action is executed.
         The value of the object tIPv6FilterParamsExtPktLenVal2 is ignored.


         tIPFilterParamsAction   |   TRUE case action  |  FALSE case action
         ------------------------------------------------------------------
         drop                    |      drop           |      forward


         Allowed ranges for the values of tIPv6FilterParamsExtPktLenVal1 and
         tIPv6FilterParamsExtPktLenVal2 are:

         Operator                |Packet Length Value 1|Packet Length Value 2
         --------------------------------------------------------------------
         none (0)                |      N/A            |      N/A
         eq(1)                   |    0..65535         |      N/A
         range(2)                |    0..65534         | (Value1 + 1)..65535
         lt(3)                   |    1..65535         |      N/A
         gt(4)                   |    0..65534         |      N/A


         The values of the objects tIPv6FilterParamsExtPktLenVal1 and
         tIPv6FilterParamsExtPktLenVal2 are silently cleared if the value
         of this object is set to default.

         Note that the value of this object is silently cleared by the system
         if tIPv6FilterParamsAction is set to a value other than 'drop (1)'
         or
         if tIPv6FilterParamsExtHopLimitOper is set to a value other
         than 'none (0)'."
    DEFVAL { none }
    ::= { tIPv6FilterParamsExtEntry 7 }

tIPv6FilterParamsExtHopLimitVal1 OBJECT-TYPE
    SYNTAX      TFilterTTL
    MAX-ACCESS  read-create
    STATUS      current
    DESCRIPTION
        "The value of the object tIPv6FilterParamsExtHopLimitVal1 specifies
         the Hop Limit value1 to be compared to the value of
         the Hop Limit field of an IPv6 packet header that has hit this
         filter's entry.

         The way how the value of this object is used depends on the value
         of the object tIPv6FilterParamsExtHopLimitOper.

         The value of this object can be set to a non-default value only
         if the value of the object tIPv6FilterParamsExtHopLimitOper is other
         than 'none (0)'.

         If the value of tIPv6FilterParamsExtHopLimitOper is 'range (2)' then
         the value of this object must be less than the value
         of tIPv6FilterParamsExtHopLimitVal2.

         If the value of tIPv6FilterParamsExtHopLimitOper is 'lt (3)' then
         the value of this object can be set in range 1..255.

         If the value of tIPv6FilterParamsExtHopLimitOper is 'gt (4)' then
         the value of this object can be set in range 0..254.

         If both the values of the objects tIPv6FilterParamsExtHopLimitOper and
         tIPv6FilterParamsExtHopLimitVal1 need to be changed then it must be
         done in the same SET SNMP request.

         Note that the value of this object is silently cleared by the system
         if tIPv6FilterParamsAction is set to a value other than 'drop (1)'
         or
         if tIPv6FilterParamsExtHopLimitOper is set to 'none (0)'
         or
         if tIPv6FilterParamsExtPktLenOper is set to a value other
         than 'none (0)'."
    DEFVAL { 0 }
    ::= { tIPv6FilterParamsExtEntry 8 }

tIPv6FilterParamsExtHopLimitVal2 OBJECT-TYPE
    SYNTAX      TFilterTTL
    MAX-ACCESS  read-create
    STATUS      current
    DESCRIPTION
        "The value of the object tIPv6FilterParamsExtHopLimitVal2 specifies
         the Hop Limit value2 to be compared to the value of
         the Hop Limit field of an IPv6 packet header that has hit this
         filter's entry.

         The way how the value of this object is used depends on the value
         of the object tIPv6FilterParamsExtHopLimitOper.

         The value of this object can be set to a non-default value only
         if the value of the object tIPv6FilterParamsExtHopLimitOper is
         'range (2)'.

         The value of this object must be greater than the value
         of tIPv6FilterParamsExtHopLimitVal1.

         If both the values of the objects tIPv6FilterParamsExtHopLimitOper and
         tIPv6FilterParamsExtHopLimitVal2 need to be changed then it must be
         done in the same SET SNMP request.

         Note that the value of this object is silently cleared by the system
         if tIPv6FilterParamsAction is set to a value other than 'drop (1)'
         or
         if tIPv6FilterParamsExtHopLimitOper is set to a value other than
         'range (2)'
         or
         if tIPv6FilterParamsExtPktLenOper is set to a value other than
         'none (0)'."
    DEFVAL { 0 }
    ::= { tIPv6FilterParamsExtEntry 9 }

tIPv6FilterParamsExtHopLimitOper OBJECT-TYPE
    SYNTAX      TOperator
    MAX-ACCESS  read-create
    STATUS      current
    DESCRIPTION
        "The value of the object tIPv6FilterParamsExtHopLimitOper specifies
         the way how the values of the objects tIPv6FilterParamsExtHopLimitVal1
         and tIPv6FilterParamsExtHopLimitVal2 are used to form a condition
         that must be fulfilled in order to execute the action specified
         by the value of tIPv6FilterParamsAction. Otherwise the opposite action
         is executed.

         The value of this object can be set to a non-default value only if
         the value of the object tIPv6FilterParamsAction is 'drop (1)'.

         If the value of this object is being changed from the default value
         to any non-default value the values of the objects
         tIPv6FilterParamsExtHopLimitVal1 and tIPv6FilterParamsExtHopLimitVal2
         (if applicable) must be sent in the same SET SNMP request.

         If the value of this object is 'none (0)' than the values of
         the objects tIPv6FilterParamsExtHopLimitVal1 and
         tIPv6FilterParamsExtHopLimitVal2 are ignored and TRUE case action is
         always executed (see table below).

         If the value of this object is 'eq (1)' then the value of
         the Hop Limit field of the IPv6 header of the packet that has matched
         this filter's entry must be equal to the value of the object
         tIPv6FilterParamsExtHopLimitVal1 in order to execute the TRUE case
         action (see table below). Otherwise the FALSE case action is executed.
         The value of the object tIPv6FilterParamsExtHopLimitVal2 is ignored.

         If the value of this object is 'range (2)' then the value of
         the Hop Limit field of the IPv6 header of the packet that has matched
         this filter's entry must be greater than or equal to the value of
         the object tIPv6FilterParamsExtHopLimitVal1 and less than or equal to
         the value of the object tIPv6FilterParamsExtHopLimitVal2 in order
         to execute the TRUE case action (see table below). Otherwise the FALSE
         case action is executed.

         If the value of this object is 'lt (3)' then the value of
         the Hop Limit field of the IPv6 header of the packet that has matched
         this filter's entry must be less than the value of the object
         tIPv6FilterParamsExtHopLimitVal1 in order to execute the TRUE case
         action (see table below). Otherwise the FALSE case action is executed.
         The value of the object tIPv6FilterParamsExtHopLimitVal2 is ignored.

         If the value of this object is 'gt (4)' then the value of
         the Hop Limit field of the IPv6 header of the packet that has matched
         this filter's entry must be greater than the value of the object
         tIPv6FilterParamsExtHopLimitVal1 in order to execute the TRUE case
         action (see table below). Otherwise the FALSE case action is executed.
         The value of the object tIPv6FilterParamsExtHopLimitVal2 is ignored.


         tIPv6FilterParamsAction |   TRUE case action  |  FALSE case action
         ------------------------------------------------------------------
         drop                    |      drop           |      forward


         Allowed ranges for the values of tIPv6FilterParamsExtHopLimitVal1 and
         tIPv6FilterParamsExtHopLimitVal2 are:

         Operator                |  Hop Limit Value 1  |  Hop Limit Value 2
         --------------------------------------------------------------------
         none (0)                |      N/A            |      N/A
         eq(1)                   |    0..255           |      N/A
         range(2)                |    0..254           | (Value1 + 1)..255
         lt(3)                   |    1..255           |      N/A
         gt(4)                   |    0..254           |      N/A


         The values of the objects tIPv6FilterParamsExtHopLimitVal1 and
         tIPv6FilterParamsExtHopLimitVal2 are silently cleared if the value
         of this object is set to default.

         Note that the value of this object is silently cleared by the system
         if tIPv6FilterParamsAction is set to a value other than 'drop (1)'
         or
         if tIPv6FilterParamsExtPktLenOper is set to a value other than
         'none (0)'."
    DEFVAL { none }
    ::= { tIPv6FilterParamsExtEntry 10 }

tIPv6FilterParamsExtEgressPBR OBJECT-TYPE
    SYNTAX      TFilterEgressPBR
    MAX-ACCESS  read-create
    STATUS      current
    DESCRIPTION
    "The value of the object tIPv6FilterParamsExtEgressPBR specifies if PBR
    specified by tIPv6FilterParamsExtEntry will have effect when the filter
    is applied on egress.
    tIPv6FilterParamsExtEgressPBR is applicable with these configured
    actions and action state:
    - no action
    - action forward redirect-policy <policy-name>
    - action forward esi <esi> sf-ip <ipv6-address>
      vas-interface <interface-name> router <router-instance>
    - action forward esi <esi> sf-ip <ipv6-address>
      vas-interface <interface-name> router service-name <service-name>
    - action forward next-hop <ipv6-address>
    - action forward next-hop <ipv6-address> router <router-instance>
    - action forward next-hop <ipv6-address> router service-name <service-name>
    - action forward next-hop indirect <ipv6-address>
    - action forward next-hop indirect <ipv6-address> router <router-instance>
    - action forward next-hop indirect <ipv6-address> router
      service-name <service-name>
    "
    DEFVAL { disable }
    ::= { tIPv6FilterParamsExtEntry 11 }

tIPv6FilterParamsExtEsi OBJECT-TYPE
    SYNTAX      TFilterEsi
    MAX-ACCESS  read-create
    STATUS      current
    DESCRIPTION
        "The value of the object tIPv6FilterParamsExtEsi specifies the ethernet
         segment identifier (ESI). ESI is mapped by BGP EVPN to an L2 or L3
         capable appliance based on the value of tIPv6FilterParamsAction.
         Packets matching this entry are steered toward the L2 or L3
         appliance.

         The value '0' indicates that there is no ESI specified.

         There are two options how to set the value of tIPv6FilterParamsExtEsi:
         1. Non zero value of tIPv6FilterParamsExtEsi is set together with non
            zero values of tIPv6FilterParamsExtFwdEsiVRtrId,
            tIPv6FilterParamsExtFwdEsiVasIf and tIPv6FilterParamsExtFwdEsiSFIp.
            In this case value of tIPv6FilterParamsAction is set to
            'forwardEsiL3' by the system.

         2. Non zero value of tIPv6FilterParamsExtEsi is set together with a
            non zero value of tIPv6FilterParamsExtFwdEsiSvcId. In this case
            value of tIPv6FilterParamsAction is set to 'forwardEsiL2' by
            the system.

         Note: The value of tIPv6FilterParamsExtEsi is set to '0' by the system
         if the value of tIPv6FilterParamsAction is set to any value other than
         'forwardEsiL2' or 'forwardEsiL3'."
    DEFVAL { '00000000000000000000'H }
    ::= { tIPv6FilterParamsExtEntry 12 }

tIPv6FilterParamsExtFwdEsiSvcId OBJECT-TYPE
    SYNTAX      TmnxServId
    MAX-ACCESS  read-create
    STATUS      current
    DESCRIPTION
        "The value of the object tIPv6FilterParamsExtFwdEsiSvcId specifies the
         identifier of VPLS used for VPN/DC connectivity.

         The value '0' indicates that there is no VPLS identifier specified.

         The non zero value of tIPv6FilterParamsExtFwdEsiSvcId must be set
         together with a non zero value of tIPv6FilterParamsExtEsi.

         Note: The value of tIPv6FilterParamsExtFwdEsiSvcId is set to '0' by
         the system if the value of the object tIPv6FilterParamsAction is set
         to any value other than 'forwardEsiL2'."
    DEFVAL { 0 }
    ::= { tIPv6FilterParamsExtEntry 13 }


tIPv6FilterParamsExtFwdEsiVRtrId OBJECT-TYPE
    SYNTAX      TmnxVRtrIDOrZero
    MAX-ACCESS  read-create
    STATUS      current
    DESCRIPTION
        "The value of the object tIPv6FilterParamsExtFwdEsiVRtrId specifies the
         VPRN/rVPLS virtual router identifier used for VPN/DC connectivity.

         The value '0' indicates that there is no VPRN/rVPLS virtual router
         identifier specified.

         The non zero value of tIPv6FilterParamsExtFwdEsiVRtrId must be set
         together with non zero values of tIPv6FilterParamsExtEsi,
         tIPv6FilterParamsExtFwdEsiVasIf and tIPv6FilterParamsExtFwdEsiSFIp.

         Note: The value of tIPv6FilterParamsExtFwdEsiVRtrId is set to '0' by
         the system if the value of tIPv6FilterParamsAction is set to any value
         other than 'forwardEsiL3'."
    DEFVAL { 0 }
    ::= { tIPv6FilterParamsExtEntry 14 }

tIPv6FilterParamsExtFwdEsiSFIp OBJECT-TYPE
    SYNTAX      InetAddressIPv6
    MAX-ACCESS  read-create
    STATUS      current
    DESCRIPTION
        "The value of the object tIPv6FilterParamsExtFwdEsiSFIp specifies the
         IPv6 address of the service function toward which traffic is steered.

         The value '0' indicates that no service function IP address is
         specified.

         The non zero value of tIPv6FilterParamsExtFwdEsiSFIp must be set
         together with non zero values of tIPv6FilterParamsExtFwdEsiVRtrId,
         tIPv6FilterParamsExtFwdEsiVasIf and tIPv6FilterParamsExtEsi.

         Note: The value of tIPv6FilterParamsExtFwdEsiSFIp is set to '0' by the
         system if the value of tIPv6FilterParamsAction is set to any value
         other than 'forwardEsiL3'."
    DEFVAL { '00000000000000000000000000000000'H }

    ::= { tIPv6FilterParamsExtEntry 15 }


tIPv6FilterParamsExtPbrDwnActOvr OBJECT-TYPE
    SYNTAX      TFilterPbrDownActionOvr
    MAX-ACCESS  read-create
    STATUS      current
    DESCRIPTION
        "The value of the object tIPv6FilterParamsExtPbrDwnActOvr specifies the
         filter action which will be performed when the PBR/PBF target for this
         entry is not available.

         If the value of tIPvXFltrEntryActAction is not one of the following
         values then tIPv6FilterParamsExtPbrDwnActOvr must be set to the value
         'none':
         - forwardEsiL2
         - forwardEsiL3
         - forwardSap
         - forwardSdp
         - forwardNextHopRtr

         If the value of tIPFilterParamsExtPbrDwnActOvr is different from 'none'
         then PBR/PBF destination availability checking for an entry is turned
         on. There is a limit to the number of filter entries with the
         destination availability checking turned on. Entries with the value of
         tIPvXFltrEntryActAction equal to 'forwardEsiL2' or 'forwardEsiL3' are
         not counted against this limit.

         Refer to the description of the textual convention
         TFilterPbrDownActionOvr for more details."
    DEFVAL { none }
    ::= { tIPv6FilterParamsExtEntry 16 }

tIPv6FilterParamsExtFwdEsiVasIf OBJECT-TYPE
    SYNTAX      InterfaceIndexOrZero
    MAX-ACCESS  read-create
    STATUS      current
    DESCRIPTION
        "The value of the object tIPv6FilterParamsExtFwdEsiVasIf specifies the
         virtual router interface index of VPRN RVPLS interface used for VPN/DC
         connectivity.

         The value '0' indicates that no interface id is specified.

         The non zero value of tIPv6FilterParamsExtFwdEsiVasIf must be set
         together with non zero values of tIPv6FilterParamsExtFwdEsiVRtrId,
         tIPv6FilterParamsExtFwdEsiSFIp and tIPv6FilterParamsExtEsi.

         Note: The value of tIPv6FilterParamsExtFwdEsiVasIf is set to '0' by the
         system if the value of tIPv6FilterParamsAction is set to any value
         other than 'forwardEsiL3'."
    DEFVAL { 0 }
    ::= { tIPv6FilterParamsExtEntry 17 }

tIPv6FilterParamsExtStickyDst OBJECT-TYPE
    SYNTAX      Integer32 (-1|0..65535)
    UNITS       "seconds"
    MAX-ACCESS  read-create
    STATUS      current
    DESCRIPTION
        "The value of the object tIPv6FilterParamsExtStickyDst specifies how
         long will system wait (in seconds) until it activates the best
         action (action with available PBR/PBF destination and the highest
         priority). Until then the action specified by
         tIPv6FilterParamsExtPbrDwnActOvr will be taken on a packet matching the
         filter entry. After the value of the active destination is fixed it
         will remain unchanged until the active PBR/PBF destination becomes
         unreachable.

         The value of -1 indicates that the property of PBR destination
         stickiness is turned off. When the property of stickiness is turned off
         the active PBR/PBF destination is always the one which is available and
         has the highest priority.

         The countdown starts when there was no PBR/PBF destination reachable
         and any PBR/PBF destination becomes reachable.

         tIPv6FilterParamsExtStickyDst can be set to value other than -1 only if
         the value of tIPvXFltrEntryActAction is one of the following values:
         - forwardSap
         - forwardSdp
         - forwardNextHopRtr
         "
    DEFVAL { -1 }
    ::= { tIPv6FilterParamsExtEntry 18 }

tIPv6FilterParamsExtHoldRemain OBJECT-TYPE
    SYNTAX      Integer32 (0..65535)
    MAX-ACCESS  read-only
    STATUS      current
    DESCRIPTION
        "The value of the object tIPv6FilterParamsExtHoldRemain indicates the
         remaining time in seconds, until the best action will become active
         and will be fixed.

         Best action is:
         - primary action if PBR target status of primary action is up.
         - secondary action if PBR target status of secondary action is up
           and PBR target status of primary action is down.
         - none if both PBR targets are down
         "
    ::= { tIPv6FilterParamsExtEntry 19 }

tIPv6FilterParamsExtDownloadAct OBJECT-TYPE
    SYNTAX      TFilterDownloadedAction
    MAX-ACCESS  read-only
    STATUS      current
    DESCRIPTION
        "The value of the object tIPv6FilterParamsExtDownloadAct indicates
         the filter entry action downloaded to IOM.

         Refer to the description of the textual convention
         TFilterDownloadedAction for more information."
    ::= { tIPv6FilterParamsExtEntry 20 }

----------------------------------------
------- tIPFilterParamsExtTable --------
----------------------------------------

tIPFilterParamsExtTbleLstChgd OBJECT-TYPE
    SYNTAX      TimeStamp
    MAX-ACCESS  read-only
    STATUS      current
    DESCRIPTION
        "The value of tIPFilterParamsExtTbleLstChgd indicates the
         sysUpTime at the time of the last modification
         of tIPFilterParamsExtTable.

         If no changes were made to the entry since the last
         re-initialization of the local network management subsystem,
         then this object contains a zero value."
    ::= { tFilterObjects 52 }

tIPFilterParamsExtTable OBJECT-TYPE
    SYNTAX      SEQUENCE OF TIPFilterParamsExtEntry
    MAX-ACCESS  not-accessible
    STATUS      current
    DESCRIPTION
        "The table tIPFilterParamsExtTable contains, together with the
         table tIPFilterParamsTable info about every IP filter entry in
         any of the configured IP filters in the system.

         The table tIPFilterParamsExtTable was introduced due to the big size
         of the tIPFilterParamsTable."
    ::= { tFilterObjects 53 }

tIPFilterParamsExtEntry OBJECT-TYPE
    SYNTAX      TIPFilterParamsExtEntry
    MAX-ACCESS  not-accessible
    STATUS      current
    DESCRIPTION
        "Information about a particular IP Filter entry.
         Every IP Filter can have zero or more IP Filter match entries.

         A filter entry with no match criteria set will match every
         packet, and the entry action will be taken.

         Entries are created/deleted by the system when a corresponding
         tIPFilterParamsEntry is created/deleted.

         Additional match criteria can be found in tIPFilterParamsTable."
    AUGMENTS {tIPFilterParamsEntry}
    ::= { tIPFilterParamsExtTable 1 }

TIPFilterParamsExtEntry ::= SEQUENCE
    {
        tIPFilterParamsExtLastChanged         TimeStamp,
        tIPFilterParamsExtPktLenVal1          TFilterPacketLength,
        tIPFilterParamsExtPktLenVal2          TFilterPacketLength,
        tIPFilterParamsExtPktLenOper          TOperator,
        tIPFilterParamsExtTTLVal1             TFilterTTL,
        tIPFilterParamsExtTTLVal2             TFilterTTL,
        tIPFilterParamsExtTTLOper             TOperator,
        tIPFilterParamsExtEgressPBR           TFilterEgressPBR,
        tIPFilterParamsExtEsi                 TFilterEsi,
        tIPFilterParamsExtFwdEsiSvcId         TmnxServId,
        tIPFilterParamsExtFwdEsiVRtrId        TmnxVRtrIDOrZero,
        tIPFilterParamsExtFwdEsiSFIp          InetAddressIPv4,
        tIPFilterParamsExtPbrDwnActOvr        TFilterPbrDownActionOvr,
        tIPFilterParamsExtFwdEsiVasIf         InterfaceIndexOrZero,
        tIPFilterParamsExtStickyDst           Integer32,
        tIPFilterParamsExtHoldRemain          Integer32,
        tIPFilterParamsExtDownloadAct         TFilterDownloadedAction
    }

tIPFilterParamsExtLastChanged OBJECT-TYPE
    SYNTAX      TimeStamp
    MAX-ACCESS  read-only
    STATUS      current
    DESCRIPTION
        "The value of the object tIPFilterParamsExtLastChanged indicates
        the timestamp of last change of this row in tIPFilterParamsExtTable."
    ::= { tIPFilterParamsExtEntry 1 }

tIPFilterParamsExtPktLenVal1 OBJECT-TYPE
    SYNTAX      TFilterPacketLength
    MAX-ACCESS  read-create
    STATUS      current
    DESCRIPTION
        "The value of the object tIPFilterParamsExtPktLenVal1 specifies
         the packet length value1 to be compared to the value of the Total
         Length field of an IP packet header that has hit this filter's entry.

         The way how the value of this object is used depends on the value
         of the object tIPFilterParamsExtPktLenOper.

         The value of this object can be set to a non-default value only
         if the value of the object tIPFilterParamsExtPktLenOper is other
         than 'none (0)'.

         If the value of tIPFilterParamsExtPktLenOper is 'range (2)' then
         the value of this object must be less than the value
         of tIPFilterParamsExtPktLenVal2.

         If the value of tIPFilterParamsExtPktLenOper is 'lt (3)' then
         the value of this object can be set in range 1..65535.

         If the value of tIPFilterParamsExtPktLenOper is 'gt (4)' then
         the value of this object can be set in range 0..65534.

         If both the values of the objects tIPFilterParamsExtPktLenOper and
         tIPFilterParamsExtPktLenVal1 need to be changed then it must be
         done in the same SET SNMP request.

         Note that the value of this object is silently cleared by the system
         if tIPFilterParamsAction is set to a value other than 'drop (1)'
         or
         if tIPFilterParamsExtPktLenOper is set to 'none (0)'
         or
         if tIPFilterParamsExtTTLOper is set to a value other
         than 'none (0)'.
         "
    DEFVAL { 0 }
    ::= { tIPFilterParamsExtEntry 2 }

tIPFilterParamsExtPktLenVal2 OBJECT-TYPE
    SYNTAX      TFilterPacketLength
    MAX-ACCESS  read-create
    STATUS      current
    DESCRIPTION
        "The value of the object tIPFilterParamsExtPktLenVal2 specifies
         the packet length value2 to be compared to the value of the Total
         Length field of an IP packet header that has hit this filter's entry.

         The way how the value of this object is used depends on the value
         of the object tIPFilterParamsExtPktLenOper.

         The value of this object can be set to a non-default value only
         if the value of the object tIPFilterParamsExtPktLenOper is 'range (2)'.

         The value of this object must be greater than the value
         of tIPFilterParamsExtPktLenVal1.

         If both the values of the objects tIPFilterParamsExtPktLenOper and
         tIPFilterParamsExtPktLenVal2 need to be changed then it must be
         done in the same SET SNMP request.

         Note that the value of this object is silently cleared by the system
         if tIPFilterParamsAction is set to a value other than 'drop (1)'
         or
         if tIPFilterParamsExtPktLenOper is set to value other than
         'range (2)'
         or
         if tIPFilterParamsExtTTLOper is set to a value other
         than 'none (0)'.
         "
    DEFVAL { 0 }
    ::= { tIPFilterParamsExtEntry 3 }

tIPFilterParamsExtPktLenOper OBJECT-TYPE
    SYNTAX      TOperator
    MAX-ACCESS  read-create
    STATUS      current
    DESCRIPTION
        "The value of the object tIPFilterParamsExtPktLenOper specifies the way
         how the values of the objects tIPFilterParamsExtPktLenVal1 and
         tIPFilterParamsExtPktLenVal2 are used to form a condition that must
         be fulfilled in order to execute the action specified by the value
         of tIPFilterParamsAction. Otherwise the opposite action is executed.

         The value of this object can be set to a non-default value only if
         the value of the object tIPFilterParamsAction is 'drop (1)'.

         If the value of this object is being changed from the default value
         to any non-default value the values of the objects
         tIPFilterParamsExtPktLenVal1 and tIPFilterParamsExtPktLenVal2
         (if applicable) must be sent in the same SET SNMP request.

         If the value of this object is 'none (0)' than the values of
         the objects tIPFilterParamsExtPktLenVal1 and
         tIPFilterParamsExtPktLenVal2 are ignored and TRUE case action is
         always executed (see table below).

         If the value of this object is 'eq (1)' then the value of the Total
         Length field of the IP header of the packet that has matched this
         filter's entry must be equal to the value of the object
         tIPFilterParamsExtPktLenVal1 in order to execute the TRUE case action
         (see table below). Otherwise the FALSE case action is executed.
         The value of the object tIPFilterParamsExtPktLenVal2 is ignored.

         If the value of this object is 'range (2)' then the value of the Total
         Length field of the IP header of the packet that has matched this
         filter's entry must be greater than or equal to the value of the object
         tIPFilterParamsExtPktLenVal1 and less than or equal to the value
         of the object tIPFilterParamsExtPktLenVal2 in order to execute
         the TRUE case action (see table below). Otherwise the FALSE case action
         is executed.

         If the value of this object is 'lt (3)' then the value of the Total
         Length field of the IP header of the packet that has matched this
         filter's entry must be less than the value of the object
         tIPFilterParamsExtPktLenVal1 in order to execute the TRUE case action
         (see table below). Otherwise the FALSE case action is executed.
         The value of the object tIPFilterParamsExtPktLenVal2 is ignored.

         If the value of this object is 'gt (4)' then the value of the Total
         Length field of the IP header of the packet that has matched this
         filter's entry must be greater than the value of the object
         tIPFilterParamsExtPktLenVal1 in order to execute the TRUE case action
         (see table below). Otherwise the FALSE case action is executed.
         The value of the object tIPFilterParamsExtPktLenVal2 is ignored.


         tIPFilterParamsAction   |   TRUE case action  |  FALSE case action
         ------------------------------------------------------------------
         drop                    |      drop           |      forward


         Allowed ranges for the values of tIPFilterParamsExtPktLenVal1 and
         tIPFilterParamsExtPktLenVal2 are:

         Operator                |Packet Length Value 1|Packet Length Value 2
         --------------------------------------------------------------------
         none (0)                |      N/A            |      N/A
         eq(1)                   |    0..65535         |      N/A
         range(2)                |    0..65534         | (Value1 + 1)..65535
         lt(3)                   |    1..65535         |      N/A
         gt(4)                   |    0..65534         |      N/A


         The values of the objects tIPFilterParamsExtPktLenVal1 and
         tIPFilterParamsExtPktLenVal2 are silently cleared if the value of this
         object is set to default.

         Note that the value of this object is silently cleared by the system
         if tIPFilterParamsAction is set to a value other than 'drop (1)'
         or
         if tIPFilterParamsExtTTLOper is set to a value other than 'none (0)'.
         "
    DEFVAL { none }
    ::= { tIPFilterParamsExtEntry 4 }

tIPFilterParamsExtTTLVal1 OBJECT-TYPE
    SYNTAX      TFilterTTL
    MAX-ACCESS  read-create
    STATUS      current
    DESCRIPTION
        "The value of the object tIPFilterParamsExtTTLVal1 specifies
         the Time-To-Live value1 to be compared to the value of
         the Time-To-Live field of an IP packet header that has hit this
         filter's entry.

         The way how the value of this object is used depends on the value
         of the object tIPFilterParamsExtTTLOper.

         The value of this object can be set to a non-default value only
         if the value of the object tIPFilterParamsExtTTLOper is other
         than 'none (0)'.

         If the value of tIPFilterParamsExtTTLOper is 'range (2)' then
         the value of this object must be less than the value
         of tIPFilterParamsExtTTLVal2.

         If the value of tIPFilterParamsExtTTLOper is 'lt (3)' then
         the value of this object can be set in range 1..255.

         If the value of tIPFilterParamsExtTTLOper is 'gt (4)' then
         the value of this object can be set in range 0..254.

         If both the values of the objects tIPFilterParamsExtTTLOper and
         tIPFilterParamsExtTTLVal1 need to be changed then it must be
         done in the same SET SNMP request.

         Note that the value of this object is silently cleared by the system
         if tIPFilterParamsAction is set to a value other than 'drop (1)'
         or
         if tIPFilterParamsExtTTLOper is set to 'none (0)'
         or
         if tIPFilterParamsExtPktLenOper is set to a value other
         than 'none (0)'."
    DEFVAL { 0 }
    ::= { tIPFilterParamsExtEntry 5 }

tIPFilterParamsExtTTLVal2 OBJECT-TYPE
    SYNTAX      TFilterTTL
    MAX-ACCESS  read-create
    STATUS      current
    DESCRIPTION
        "The value of the object tIPFilterParamsExtTTLVal2 specifies
         the Time-To-Live value2 to be compared to the value of
         the Time-To-Live field of an IP packet header that has hit this
         filter's entry.

         The way how the value of this object is used depends on the value
         of the object tIPFilterParamsExtTTLOper.

         The value of this object can be set to a non-default value only
         if the value of the object tIPFilterParamsExtTTLOper is 'range (2)'.

         The value of this object must be greater than the value
         of tIPFilterParamsExtTTLVal1.

         If both the values of the objects tIPFilterParamsExtTTLOper and
         tIPFilterParamsExtTTLVal2 need to be changed then it must be
         done in the same SET SNMP request.

         Note that the value of this object is silently cleared by the system
         if tIPFilterParamsAction is set to a value other than 'drop (1)'
         or
         if tIPFilterParamsExtTTLOper is set to a value other than
         'range (2)'
         or
         if tIPFilterParamsExtPktLenOper is set to a value other than
         'none (0)'."
    DEFVAL { 0 }
    ::= { tIPFilterParamsExtEntry 6 }

tIPFilterParamsExtTTLOper OBJECT-TYPE
    SYNTAX      TOperator
    MAX-ACCESS  read-create
    STATUS      current
    DESCRIPTION
        "The value of the object tIPFilterParamsExtTTLOper specifies the way
         how the values of the objects tIPFilterParamsExtTTLVal1 and
         tIPFilterParamsExtTTLVal2 are used to form a condition that must
         be fulfilled in order to execute the action specified by the value
         of tIPFilterParamsAction. Otherwise the opposite action is executed.

         The value of this object can be set to a non-default value only if
         the value of the object tIPFilterParamsAction is 'drop (1)'.

         If the value of this object is being changed from the default value
         to any non-default value the values of the objects
         tIPFilterParamsExtTTLVal1 and tIPFilterParamsExtTTLVal2
         (if applicable) must be sent in the same SET SNMP request.

         If the value of this object is 'none (0)' than the values of
         the objects tIPFilterParamsExtTTLVal1 and
         tIPFilterParamsExtTTLVal2 are ignored and TRUE case action is
         always executed (see table below).

         If the value of this object is 'eq (1)' then the value of
         the Time-To-Live field of the IP header of the packet that has matched
         this filter's entry must be equal to the value of the object
         tIPFilterParamsExtTTLVal1 in order to execute the TRUE case action
         (see table below). Otherwise the FALSE case action is executed.
         The value of the object tIPFilterParamsExtTTLVal2 is ignored.

         If the value of this object is 'range (2)' then the value of
         the Time-To-Live field of the IP header of the packet that has matched
         this filter's entry must be greater than or equal to the value of
         the object tIPFilterParamsExtTTLVal1 and less than or equal to
         the value of the object tIPFilterParamsExtTTLVal2 in order to execute
         the TRUE case action (see table below). Otherwise the FALSE case
         action is executed.

         If the value of this object is 'lt (3)' then the value of
         the Time-To-Live field of the IP header of the packet that has matched
         this filter's entry must be less than the value of the object
         tIPFilterParamsExtTTLVal1 in order to execute the TRUE case action
         (see table below). Otherwise the FALSE case action is executed.
         The value of the object tIPFilterParamsExtTTLVal2 is ignored.

         If the value of this object is 'gt (4)' then the value of
         the Time-To-Live field of the IP header of the packet that has matched
         this filter's entry must be greater than the value of the object
         tIPFilterParamsExtTTLVal1 in order to execute the TRUE case action
         (see table below). Otherwise the FALSE case action is executed.
         The value of the object tIPFilterParamsExtTTLVal2 is ignored.


         tIPFilterParamsAction   |   TRUE case action  |  FALSE case action
         ------------------------------------------------------------------
         drop                    |      drop           |      forward


         Allowed ranges for the values of tIPFilterParamsExtTTLVal1 and
         tIPFilterParamsExtTTLVal2 are:

         Operator                | Time-To-Live Value 1| Time-To-Live Value 2
         --------------------------------------------------------------------
         none (0)                |      N/A            |      N/A
         eq(1)                   |    0..255           |      N/A
         range(2)                |    0..254           | (Value1 + 1)..255
         lt(3)                   |    1..255           |      N/A
         gt(4)                   |    0..254           |      N/A


         The values of the objects tIPFilterParamsExtTTLVal1 and
         tIPFilterParamsExtTTLVal2 are silently cleared if the value of this
         object is set to default.

         Note that the value of this object is silently cleared by the system
         if tIPFilterParamsAction is set to a value other than 'drop (1)'
         or
         if tIPFilterParamsExtPktLenOper is set to a value other than
         'none (0)'."
    DEFVAL { none }
    ::= { tIPFilterParamsExtEntry 7 }

tIPFilterParamsExtEgressPBR OBJECT-TYPE
    SYNTAX      TFilterEgressPBR
    MAX-ACCESS  read-create
    STATUS      current
    DESCRIPTION
    "The value of the object tIPFilterParamsExtEgressPBR specifies if PBR
    specified by tIPFilterParamsExtEntry will have effect when the filter
    is applied on egress.
    tIPFilterParamsExtEgressPBR is applicable with these configured
    actions and action state:
    - no action
    - action forward redirect-policy <policy-name>
    - action forward esi <esi> sf-ip <ip-address> vas-interface <interface-name>
      router <router-instance>
    - action forward esi <esi> sf-ip <ip-address> vas-interface <interface-name>
      router service-name <service-name>
    - action forward next-hop <ip-address>
    - action forward next-hop <ip-address> router <router-instance>
    - action forward next-hop <ip-address> router service-name <service-name>
    - action forward next-hop indirect <ip-address>
    - action forward next-hop indirect <ip-address> router <router-instance>
    - action forward next-hop indirect <ip-address> router
      service-name <service-name>
    "
    DEFVAL { disable }
    ::= { tIPFilterParamsExtEntry 8 }

tIPFilterParamsExtEsi OBJECT-TYPE
    SYNTAX      TFilterEsi
    MAX-ACCESS  read-create
    STATUS      current
    DESCRIPTION
        "The value of the object tIPFilterParamsExtEsi specifies the ethernet
         segment identifier (ESI). ESI is mapped by BGP EVPN to an L2 or L3
         capable appliance based on the value of tIPFilterParamsAction. Packets
         matching this entry are steered toward the L2 or L3 appliance.

         The value '0' indicates that there is no ESI specified.

         There are two options how to set the value of tIPFilterParamsExtEsi:
         1. Non zero value of tIPFilterParamsExtEsi is set together with non
            zero values of tIPFilterParamsExtFwdEsiVRtrId,
            tIPFilterParamsExtFwdEsiVasIf and tIPFilterParamsExtFwdEsiSFIp. In
            this case value of tIPFilterParamsAction is set to 'forwardEsiL3' by
            the system.

         2. Non zero value of tIPFilterParamsExtEsi is set together with a non
            zero value of tIPFilterParamsExtFwdEsiSvcId. In this case value of
            tIPFilterParamsAction is set to 'forwardEsiL2' by the system.

         Note: The value of tIPFilterParamsExtEsi is set to '0' by the system
         if the value of tIPFilterParamsAction is set to any value other than
         'forwardEsiL2' or 'forwardEsiL3'."
    DEFVAL { '00000000000000000000'H }
    ::= { tIPFilterParamsExtEntry 9 }

tIPFilterParamsExtFwdEsiSvcId OBJECT-TYPE
    SYNTAX      TmnxServId
    MAX-ACCESS  read-create
    STATUS      current
    DESCRIPTION
        "The value of the object tIPFilterParamsExtFwdEsiSvcId specifies
         the identifier of a VPLS used for VPN/DC connectivity.

         The value '0' indicates that there is no VPLS identifier specified.

         The non zero value of tIPFilterParamsExtFwdEsiSvcId must be set
         together with a non zero value of tIPFilterParamsExtEsi.

         Note: The value of tIPFilterParamsExtFwdEsiSvcId is set to '0' by the
         system if the value of tIPFilterParamsAction is set to
         any value other than 'forwardEsiL2'."
    DEFVAL { 0 }
    ::= { tIPFilterParamsExtEntry 10 }

tIPFilterParamsExtFwdEsiVRtrId OBJECT-TYPE
    SYNTAX      TmnxVRtrIDOrZero
    MAX-ACCESS  read-create
    STATUS      current
    DESCRIPTION
       "The value of the object tIPFilterParamsExtFwdEsiVRtrId specifies the
        VPRN/rVPLS virtual router identifier used for VPN/DC connectivity.

        The value '0' indicates that there is no VPRN/rVPLS virtual router
        identifier specified.

        The non zero value of tIPFilterParamsExtFwdEsiVRtrId must be set
        together with non zero values of tIPFilterParamsExtEsi,
        tIPFilterParamsExtFwdEsiVasIf and tIPFilterParamsExtFwdEsiSFIp.

        Note: The value of tIPFilterParamsExtFwdEsiVRtrId is set to '0' by the
        system if the value of tIPFilterParamsAction is set to any value other
        than 'forwardEsiL3'."
    DEFVAL { 0 }
    ::= { tIPFilterParamsExtEntry 11 }

tIPFilterParamsExtFwdEsiSFIp OBJECT-TYPE
    SYNTAX      InetAddressIPv4
    MAX-ACCESS  read-create
    STATUS      current
    DESCRIPTION
        "The value of the object tIPFilterParamsExtFwdEsiSFIp specifies the IP
         address of the service function toward which traffic is steered.

         The value '0' indicates that no service function IP address is
         specified.

         The non zero value of tIPFilterParamsExtFwdEsiSFIp must be set together
         with a non zero values of tIPFilterParamsExtFwdEsiVRtrId,
         tIPFilterParamsExtFwdEsiVasIf and tIPFilterParamsExtEsi.

         Note: The value of tIPFilterParamsExtFwdEsiSFIp is set to default by
         the system if the value of tIPFilterParamsAction is set to any value
         other than 'forwardEsiL3'."
    DEFVAL { '00000000'H }
    ::= { tIPFilterParamsExtEntry 12 }

tIPFilterParamsExtPbrDwnActOvr OBJECT-TYPE
    SYNTAX      TFilterPbrDownActionOvr
    MAX-ACCESS  read-create
    STATUS      current
    DESCRIPTION
        "The value of the object tIPFilterParamsExtPbrDwnActOvr specifies the
         filter action which will be performed when the PBR/PBF target for this
         entry is not available.

         If the value of tIPvXFltrEntryActAction is not one of the following
         values then tIPFilterParamsExtPbrDwnActOvr must be set to the value
         'none':
         - forwardEsiL2
         - forwardEsiL3
         - forwardSap
         - forwardSdp
         - forwardNextHopRtr

         If the value of tIPFilterParamsExtPbrDwnActOvr is different from 'none'
         then PBR/PBF destination availability checking for an entry is turned
         on. There is a limit to the number of filter entries with the
         destination availability checking turned on. Entries with the value of
         tIPvXFltrEntryActAction equal to 'forwardEsiL2' or 'forwardEsiL3' are
         not counted against this limit.

         Refer to the description of the textual convention
         TFilterPbrDownActionOvr for more details."
    DEFVAL { none }
    ::= { tIPFilterParamsExtEntry 13 }

tIPFilterParamsExtFwdEsiVasIf OBJECT-TYPE
    SYNTAX      InterfaceIndexOrZero
    MAX-ACCESS  read-create
    STATUS      current
    DESCRIPTION
       "The value of the object tIPFilterParamsExtFwdEsiVasIf specifies the
        virtual router interface index of VPRN RVPLS interface used for VPN/DC
        connectivity.

        The value '0' indicates that no interface id is specified.

        The non zero value of tIPFilterParamsExtFwdEsiVasIf must be set together
        with a non zero values of tIPFilterParamsExtFwdEsiVRtrId,
        tIPFilterParamsExtFwdEsiSFIp and tIPFilterParamsExtEsi.

        Note: The value of tIPFilterParamsExtFwdEsiVasIf is set to '0' by the
        system if the value of tIPFilterParamsAction is set to any value
        other than 'forwardEsiL3'."
    DEFVAL { 0 }
    ::= { tIPFilterParamsExtEntry 14 }

tIPFilterParamsExtStickyDst OBJECT-TYPE
    SYNTAX      Integer32 (-1|0..65535)
    UNITS       "seconds"
    MAX-ACCESS  read-create
    STATUS      current
    DESCRIPTION
        "The value of the object tIPFilterParamsExtStickyDst specifies how long
         the system will wait (in seconds) until it activates the best action
         (action with available PBR/PBF destination and the highest priority).
         Until then the action specified by tIPFilterParamsExtPbrDwnActOvr will
         be taken on a packet matching the filter entry. After the value of the
         active destination is fixed it will remain unchanged until the active
         PBR/PBF destination becomes unreachable.

         The value of -1 indicates that the property of PBR destination
         stickiness is turned off. When the property of stickiness is turned off
         the active PBR/PBF destination is always the one which is available and
         has the highest priority.

         The countdown starts when there was no PBR/PBF destination reachable
         and any PBR/PBF destination becomes reachable.

         tIPFilterParamsExtStickyDst can be set to value other than -1 only if
         the value of tIPvXFltrEntryActAction is one of following values:
         - forwardSap
         - forwardSdp
         - forwardNextHopRtr
         "
    DEFVAL { -1 }
    ::= { tIPFilterParamsExtEntry 15 }

tIPFilterParamsExtHoldRemain OBJECT-TYPE
    SYNTAX      Integer32 (0..65535)
    MAX-ACCESS  read-only
    STATUS      current
    DESCRIPTION
        "The value of the object tIPFilterParamsExtHoldRemain indicates the
         remaining time in seconds, until the best action will become active
         and will be fixed.

         Best action is:
         - primary action if PBR target status of primary action is up.
         - secondary action if PBR target status of secondary action is up
           and PBR target status of primary action is down.
         - none if both PBR targets are down
         "
    ::= { tIPFilterParamsExtEntry 16 }

tIPFilterParamsExtDownloadAct OBJECT-TYPE
    SYNTAX      TFilterDownloadedAction
    MAX-ACCESS  read-only
    STATUS      current
    DESCRIPTION
        "The value of the object tIPFilterParamsExtDownloadAct indicates
         the filter entry action downloaded to IOM.

         Refer to the description of the textual convention
         TFilterDownloadedAction for more information."
    ::= { tIPFilterParamsExtEntry 17 }

-- ----------------------------
--  tFilterEmbedOpenflowTable
-- ----------------------------
tFilterEmbedOpenflowTableLstChg OBJECT-TYPE
    SYNTAX      TimeStamp
    MAX-ACCESS  read-only
    STATUS      current
    DESCRIPTION
        "The object tFilterEmbedOpenflowTableLstChg indicates the
        sysUpTime at the time of the last modification
        of tFilterEmbedOpenflowTable.

        If no changes were made to the table since the last
        re-initialization of the local network management subsystem,
        this object contains the value zero."
    ::= { tFilterObjects 48 }

tFilterEmbedOpenflowTable OBJECT-TYPE
    SYNTAX      SEQUENCE OF TFilterEmbedOpenflowEntry
    MAX-ACCESS  not-accessible
    STATUS      current
    DESCRIPTION
        "The table tFilterEmbedOpenflowTable contains an entry
         for each open-flow flowtable embedded in a filter with scope other
         than 'embedded'."
    ::= { tFilterObjects 49 }

tFilterEmbedOpenflowEntry OBJECT-TYPE
    SYNTAX      TFilterEmbedOpenflowEntry
    MAX-ACCESS  not-accessible
    STATUS      current
    DESCRIPTION
        "An entry in the tFilterEmbedOpenflowTable."
    INDEX {tFilterEmbedOpenflowOfsName,
           tFilterEmbedOpenflowFilterType,
           tFilterEmbedOpenflowInsertFltrId,
           tFilterEmbedOpenflowOffset}
    ::= { tFilterEmbedOpenflowTable 1 }

TFilterEmbedOpenflowEntry ::=
    SEQUENCE {
        tFilterEmbedOpenflowOfsName      TNamedItem,
        tFilterEmbedOpenflowFilterType   TFilterType,
        tFilterEmbedOpenflowInsertFltrId TConfigOrVsdFilterID,
        tFilterEmbedOpenflowOffset       TFilterEmbedOffset,
        tFilterEmbedOpenflowRowStatus    RowStatus,
        tFilterEmbedOpenflowAdminState   TmnxEmbeddedFltrAdminState,
        tFilterEmbedOpenflowOperState    TmnxEmbeddedFltrOperState,
        tFilterEmbedOflowSvcContext      Unsigned32,
        tFilterEmbedOflowSapContextPort  TmnxPortID,
        tFilterEmbedOflowSapContextEncap TmnxEncapVal,
        tFilterEmbedOflowContextType     INTEGER
    }

tFilterEmbedOpenflowOfsName OBJECT-TYPE
    SYNTAX      TNamedItem
    MAX-ACCESS  not-accessible
    STATUS      current
    DESCRIPTION
        "The value of tFilterEmbedOpenflowOfsName specifies the name
         of the open-flow switch which contains the flowtable to be inserted in 
         the filter specified by tFilterEmbedOpenflowInsertFltrId."
    ::= { tFilterEmbedOpenflowEntry 1 }

tFilterEmbedOpenflowFilterType OBJECT-TYPE
    SYNTAX      TFilterType
    MAX-ACCESS  not-accessible
    STATUS      current
    DESCRIPTION
        "The object tFilterEmbedOpenflowFilterType specifies the type of filter
         for the filter specified by tFilterEmbedOpenflowInsertFltrId."
    ::= { tFilterEmbedOpenflowEntry 2 }

tFilterEmbedOpenflowInsertFltrId OBJECT-TYPE
    SYNTAX      TConfigOrVsdFilterID
    MAX-ACCESS  not-accessible
    STATUS      current
    DESCRIPTION
        "The value of tFilterEmbedOpenflowInsertFltrId specifies the filter
         where the open-flow switch specified by tFilterEmbedOpenflowOfsName
         is to be embedded.

         Values outside of range 1..65535 are reserved for entries dynamically
         created by the system and cannot be used in any SNMP SET operation."
    ::= { tFilterEmbedOpenflowEntry 3 }

tFilterEmbedOpenflowOffset OBJECT-TYPE
    SYNTAX      TFilterEmbedOffset
    MAX-ACCESS  not-accessible
    STATUS      current
    DESCRIPTION
        "The value of tFilterEmbedOpenflowOffset specifies the offset of
         inserted entries."
    ::= { tFilterEmbedOpenflowEntry 4 }

tFilterEmbedOpenflowRowStatus OBJECT-TYPE
    SYNTAX      RowStatus
    MAX-ACCESS  read-create
    STATUS      current
    DESCRIPTION
        "The value of the object tFilterEmbedOpenflowRowStatus specifies the
         status of a row in tFilterEmbedOpenflowTable. Rows are created
         and destroyed by SNMP SET operations on this object.
         
         Only values 'active (1)', 'createAndGo(4)', and 'destroy (6)' are
         supported."
    ::= { tFilterEmbedOpenflowEntry 5 }
    
tFilterEmbedOpenflowAdminState OBJECT-TYPE
    SYNTAX      TmnxEmbeddedFltrAdminState
    MAX-ACCESS  read-create
    STATUS      current
    DESCRIPTION
        "The value of tFilterEmbedOpenflowAdminState specifies the administrative
         state of the embed request defined by this row. 
         
         If an active embedding cannot be fulfilled due to dynamic events, this 
         object will be set to 'inactive' automatically by the system. In those 
         cases, the object tFilterEmbedOpenflowOperState will indicate the failure
         reason."
    DEFVAL { active }
    ::= { tFilterEmbedOpenflowEntry 6 }    

tFilterEmbedOpenflowOperState OBJECT-TYPE
    SYNTAX      TmnxEmbeddedFltrOperState
    MAX-ACCESS  read-only
    STATUS      current
    DESCRIPTION
        "The value of tFilterEmbedOpenflowOperState indicates the operational
         state of the embed request defined by this row."
    ::= { tFilterEmbedOpenflowEntry 7 }
  
tFilterEmbedOflowSvcContext OBJECT-TYPE
    SYNTAX      Unsigned32
    MAX-ACCESS  read-create
    STATUS      current
    DESCRIPTION
        "The value of tFilterEmbedOflowSvcContext specifies the service 
        context of this open-flow embedding.
        When no service context is present, this object is equal to 
        default value."
    DEFVAL { 0 }
    ::= { tFilterEmbedOpenflowEntry 8 }
    
tFilterEmbedOflowSapContextPort OBJECT-TYPE
    SYNTAX       TmnxPortID
    MAX-ACCESS   read-create
    STATUS       current
    DESCRIPTION 
        "The value of tFilterEmbedOflowSapContextPort specifies the port-id of 
         the sap context of this open-flow embedding.
         When no sap context is present, this object is set to default value."
    DEFVAL { 0 }
    ::= { tFilterEmbedOpenflowEntry 9 }
    
tFilterEmbedOflowSapContextEncap OBJECT-TYPE
    SYNTAX       TmnxEncapVal
    MAX-ACCESS   read-create
    STATUS       current
    DESCRIPTION 
        "The value of tFilterEmbedOflowSapContextEncap specifies the encap value
         of the sap context of this open-flow embedding.
         When no sap context is present, this object is set to default value."
    DEFVAL { 0 }
    ::= { tFilterEmbedOpenflowEntry 10 }
    
tFilterEmbedOflowContextType OBJECT-TYPE
    SYNTAX      INTEGER {
                   grt     (1),
                   system  (2),
                   service (3),
                   sap     (4)
                }
    MAX-ACCESS  read-create
    STATUS      current
    DESCRIPTION
        "The value of tFilterEmbedOflowContextType specifies the context in
         which the open-flow embedding is inserted into filter.
         When no context is present, this object is set to grt value."
    DEFVAL { grt }
    ::= { tFilterEmbedOpenflowEntry 11 }
    
-- ------------------------------
--  tFilterEmbedOpenflowInfoTable
-- ------------------------------

tFilterEmbedOpenflowInfoTable OBJECT-TYPE
    SYNTAX      SEQUENCE OF TFilterEmbedOpenflowInfoEntry
    MAX-ACCESS  not-accessible
    STATUS      current
    DESCRIPTION
        "The table tFilterEmbedOpenflowInfoTable contains an entry
         for each open-flow switch embedded in a filter with scope other
         than 'embedded'.
         
         This row complements the corresponding row in the 
         tFilterEmbedOpenflowTable with read-only operational info."
    ::= { tFilterObjects 50 }

tFilterEmbedOpenflowInfoEntry OBJECT-TYPE
    SYNTAX      TFilterEmbedOpenflowInfoEntry
    MAX-ACCESS  not-accessible
    STATUS      current
    DESCRIPTION
        "An entry in the tFilterEmbedOpenflowInfoTable."
    AUGMENTS {tFilterEmbedOpenflowEntry}
    ::= { tFilterEmbedOpenflowInfoTable 1 }

TFilterEmbedOpenflowInfoEntry ::=
    SEQUENCE {
        tFltrEmbedOfInfoEntryCnt         Unsigned32,
        tFltrEmbedOfInfoEntryCntInsrtd   Unsigned32
    }

tFltrEmbedOfInfoEntryCnt OBJECT-TYPE
    SYNTAX      Unsigned32
    MAX-ACCESS  read-only
    STATUS      current
    DESCRIPTION
        "The value of tFltrEmbedOfInfoEntryCnt indicates how many entries
         are eligible for embedding from the open-flow switch specified by 
         tFilterEmbedOpenflowOfsName."
    ::= { tFilterEmbedOpenflowInfoEntry 1 }

tFltrEmbedOfInfoEntryCntInsrtd OBJECT-TYPE
    SYNTAX      Unsigned32
    MAX-ACCESS  read-only
    STATUS      current
    DESCRIPTION
        "The value of tFltrEmbedOfInfoEntryCntInsrtd indicates how many entries
         are actually placed inside the filter by the open-flow switch specified
         by tFilterEmbedOpenflowOfsName.
         
         If the object tFilterEmbedOpenflowOperState is different from 
         'in-service' this object will always be zero.
         
         Else, the difference between the value of this object and the value of 
         tFltrEmbedOfInfoEntryCnt indicates how many entries were overwritten 
         by local entries in the embedding filter."
    ::= { tFilterEmbedOpenflowInfoEntry 2 }

-- ----------------------------
-- tFilterOpenflowEntryInfoTable
-- ----------------------------

tFilterOpenflowEntryInfoTable OBJECT-TYPE
    SYNTAX      SEQUENCE OF TFilterOpenflowEntryInfoEntry
    MAX-ACCESS  not-accessible
    STATUS      current
    DESCRIPTION
        "The table tFilterOpenflowEntryInfoTable contains an entry
         for each open-flow filter entry inserted in a filter with
         scope other than 'embedded'."
    ::= { tFilterObjects 51 }

tFilterOpenflowEntryInfoEntry OBJECT-TYPE
    SYNTAX      TFilterOpenflowEntryInfoEntry
    MAX-ACCESS  not-accessible
    STATUS      current
    DESCRIPTION
        "An entry in the tFilterOpenflowEntryInfoTable.
         Rows in the tFilterOpenflowEntryInfoTable are created 
         by the SYSTEM when an open-flow switch is embedded into a filter. 
         They are destroyed by the SYSTEM when an open-flow switch embedding 
         is removed from a filter."
    INDEX {tFltrEmbedOfEntryOfsName,
           tFltrEmbedOfEntryFilterType,
           tFltrEmbedOfEntryInsertFltrId,
           tFltrEmbedOfEntryOfEntryId}
    ::= { tFilterOpenflowEntryInfoTable 1 }

TFilterOpenflowEntryInfoEntry ::=
    SEQUENCE {
        tFltrEmbedOfEntryOfsName         TNamedItem,
        tFltrEmbedOfEntryFilterType      TFilterType,
        tFltrEmbedOfEntryInsertFltrId    TConfigOrVsdFilterID,
        tFltrEmbedOfEntryOfEntryId       TEntryId,
        tFltrEmbedOfEntryInsrtEntryId    TEmbedInsrtEntryId,
        tFltrEmbedOfEntryInsrtEntryState TmnxFltrEmbeddedEntryState
    }

tFltrEmbedOfEntryOfsName OBJECT-TYPE
    SYNTAX      TNamedItem
    MAX-ACCESS  not-accessible
    STATUS      current
    DESCRIPTION
        "The value of tFltrEmbedOfEntryOfsName specifies the name
         of the open-flow switch which contains the flowtable to be inserted in 
         the filter specified by tFltrEmbedOfEntryInsertFltrId."
    ::= { tFilterOpenflowEntryInfoEntry 1 }

tFltrEmbedOfEntryFilterType OBJECT-TYPE
    SYNTAX      TFilterType
    MAX-ACCESS  not-accessible
    STATUS      current
    DESCRIPTION
        "The object tFltrEmbedOfEntryFilterType specifies the type of filter
         for the filter specified by tFltrEmbedOfEntryInsertFltrId."
    ::= { tFilterOpenflowEntryInfoEntry 2 }

tFltrEmbedOfEntryInsertFltrId OBJECT-TYPE
    SYNTAX      TConfigOrVsdFilterID
    MAX-ACCESS  not-accessible
    STATUS      current
    DESCRIPTION
        "The value of tFltrEmbedOfEntryInsertFltrId specifies the filter
         where the open-flow switch specified by tFltrEmbedOfEntryOfsName 
         is to be embedded.

         Values outside of range 1..65535 are reserved for entries dynamically
         created by the system."
    ::= { tFilterOpenflowEntryInfoEntry 3 }
 
tFltrEmbedOfEntryOfEntryId OBJECT-TYPE
    SYNTAX      TEntryId
    MAX-ACCESS  not-accessible
    STATUS      current
    DESCRIPTION
        "The value of tFltrEmbedOfEntryOfEntryId specifies the base ID of the 
         entry as determined by the priority of the corresponding flow-rule in
         the open-flow switch specified by tFltrEmbedOfEntryOfsName."
    ::= { tFilterOpenflowEntryInfoEntry 4 }

tFltrEmbedOfEntryInsrtEntryId OBJECT-TYPE
    SYNTAX      TEmbedInsrtEntryId
    MAX-ACCESS  read-only 
    STATUS      current
    DESCRIPTION
        "The value of tFltrEmbedOfEntryInsrtEntryId indicates the position 
         of the filter entry in the filter specified by 
         tFltrEmbedOfEntryInsertFltrId."  
    ::= { tFilterOpenflowEntryInfoEntry 5 }

tFltrEmbedOfEntryInsrtEntryState OBJECT-TYPE
    SYNTAX      TmnxFltrEmbeddedEntryState
    MAX-ACCESS  read-only
    STATUS      current
    DESCRIPTION
        "The value of tFltrEmbedOfEntryInsrtEntryState indicates the current 
         status of the embedding of the entry identified by 
         tFltrEmbedOfEntryOfEntryId from the open-flow switch identified by 
         tFltrEmbedOfEntryOfsName that is embedded into the filter 
         identified by tFltrEmbedOfEntryInsertFltrId."
    ::= { tFilterOpenflowEntryInfoEntry 6 }


--
-- Filter Redirect Policy Destinations (13.0 onwards)
--
tFilterRPlcyDstTableLastChg OBJECT-TYPE
    SYNTAX      TimeStamp
    MAX-ACCESS  read-only
    STATUS      current
    DESCRIPTION
        "The value of the object tFilterRPlcyDstTableLastChg
         indicates the sysUpTime at the time of the last modification
         of tFilterRPlcyDstTable.

         If no changes were made to the table since the last
         re-initialization of the local network management subsystem,
         then this object contains a zero value."
    ::= { tFilterObjects 54 }


tFilterRPlcyDstTable OBJECT-TYPE
    SYNTAX      SEQUENCE OF TFilterRPlcyDstEntry
    MAX-ACCESS  not-accessible
    STATUS      current
    DESCRIPTION
        "The table tFilterRPlcyDstTable contains information pertaining
         to Redirect Policy destinations configured on this system."
    ::= { tFilterObjects 55 }

tFilterRPlcyDstEntry OBJECT-TYPE
    SYNTAX      TFilterRPlcyDstEntry
    MAX-ACCESS  not-accessible
    STATUS      current
    DESCRIPTION
        "Entry contains information about a particular Redirect Policy
         destination.

         Rows in the table tFilterRPlcyDstTable are created and destroyed
         by SNMP SET operations on the object tFltrRPDstRowStatus."
    INDEX { tFilterRedirectPolicy,
            tFltrRPDstAddrType,
            tFltrRPDstAddr }
    ::= { tFilterRPlcyDstTable 1 }

TFilterRPlcyDstEntry ::= SEQUENCE
    {
        tFltrRPDstAddrType        InetAddressType,
        tFltrRPDstAddr            InetAddress,
        tFltrRPDstLastChanged     TimeStamp,
        tFltrRPDstRowStatus       RowStatus,
        tFltrRPDstAdminState      TmnxAdminState,
        tFltrRPDstOperState       TmnxOperState,
        tFltrRPDstDescription     TItemDescription,
        tFltrRPDstAdminPriority   Unsigned32,
        tFltrRPDstOperPriority    Unsigned32
    }

tFltrRPDstAddrType OBJECT-TYPE
    SYNTAX      InetAddressType
    MAX-ACCESS  not-accessible
    STATUS      current
    DESCRIPTION
        "The value of the object tFltrRPDstAddrType specifies the context
         in which the value of the object tFltrRPDstAddr is interpreted.

         Only the following values are supported:
            ipv4(1)
            ipv6(2)

         The value of this object must be the same for all destinations
         in a Redirect Policy."
    ::= { tFilterRPlcyDstEntry 1 }

tFltrRPDstAddr OBJECT-TYPE
    SYNTAX      InetAddress (SIZE(4|16))
    MAX-ACCESS  not-accessible
    STATUS      current
    DESCRIPTION
        "The value of the object tFltrRPDstAddr specifies the IP address
         of the destination.

         The value must be consistent with the IP version value
         of the associated tFltrRPDstAddrType object."
    ::= { tFilterRPlcyDstEntry 2 }

tFltrRPDstLastChanged OBJECT-TYPE
    SYNTAX      TimeStamp
    MAX-ACCESS  read-only
    STATUS      current
    DESCRIPTION
        "The value of the object tFltrRPDstLastChanged indicates
        the timestamp of last change of this row in tFilterRPlcyDstTable."
    ::= { tFilterRPlcyDstEntry 3 }

tFltrRPDstRowStatus OBJECT-TYPE
    SYNTAX      RowStatus
    MAX-ACCESS  read-create
    STATUS      current
    DESCRIPTION
        "The value of the object tFltrRPDstRowStatus specifies the status
         of the conceptual row in tFilterRPlcyDstTable.

         Rows can be created and destroyed by SNMP SET operations on this
         object."
    ::= { tFilterRPlcyDstEntry 4 }

tFltrRPDstAdminState OBJECT-TYPE
    SYNTAX      TmnxAdminState
    MAX-ACCESS  read-create
    STATUS      current
    DESCRIPTION
        "The value of the object tFltrRPDstAdminState specifies the configured
         administrative state of the destination.
         If the administrative state is 'outOfService' then all tests for this
         destination will not be conducted."
    DEFVAL { outOfService }
    ::= { tFilterRPlcyDstEntry 5 }

tFltrRPDstOperState OBJECT-TYPE
    SYNTAX      TmnxOperState
    MAX-ACCESS  read-only
    STATUS      current
    DESCRIPTION
        "The value of the object tFltrRPDstOperState indicates the operational
         state of the destination."
    ::= { tFilterRPlcyDstEntry 6 }

tFltrRPDstDescription OBJECT-TYPE
    SYNTAX      TItemDescription
    MAX-ACCESS  read-create
    STATUS      current
    DESCRIPTION
        "The value of the object tFltrRPDstDescription specifies
         the user-provided description for this destination."
    DEFVAL { ''H }
    ::= { tFilterRPlcyDstEntry 7 }

tFltrRPDstAdminPriority OBJECT-TYPE
    SYNTAX      Unsigned32 (1..255)
    MAX-ACCESS  read-create
    STATUS      current
    DESCRIPTION
        "The value of the object tFltrRPDstAdminPriority specifies
         the configured priority for this destination.

         The value is used as a base value for the calculation
         of the operational priority indicated by the value of the object
         tFltrRPDstOperPriority."
    DEFVAL { 100 }
    ::= { tFilterRPlcyDstEntry 8 }

tFltrRPDstOperPriority OBJECT-TYPE
    SYNTAX      Unsigned32 (0..255)
    MAX-ACCESS  read-only
    STATUS      current
    DESCRIPTION
        "The value of the object tFltrRPDstOperPriority indicates
         the current dynamic priority of this destination.

         It is derived from the base priority indicated by the value
         of the object tFltrRPDstAdminPriority and results of tests assigned
         to the destination.

         A destination with the highest operational priority across multiple
         destinations in a Redirect Policy is used as the preferred
         destination.

         If the value of the object tFltrRPDstOperState is 'outOfService' then
         the value of this object is '0'."
    ::= { tFilterRPlcyDstEntry 9 }

--
-- Filter Redirect SNMP Test Table (IPv4/IPv6)
--
tFilterRPlcySNMPTestTableLastChg OBJECT-TYPE
    SYNTAX      TimeStamp
    MAX-ACCESS  read-only
    STATUS      current
    DESCRIPTION
        "The value of the object tFilterRPlcySNMPTestTableLastChg
         indicates the sysUpTime at the time of the last modification
         of tFilterRPlcySNMPTestTable.

         If no changes were made to the table since the last
         re-initialization of the local network management subsystem,
         then this object contains a zero value."
    ::= { tFilterObjects 56 }

tFilterRPlcySNMPTestTable OBJECT-TYPE
    SYNTAX      SEQUENCE OF TFilterRPlcySNMPTestEntry
    MAX-ACCESS  not-accessible
    STATUS      current
    DESCRIPTION
        "The object tFilterRPlcySNMPTestTable contains a list
        of all redirect policies' SNMP tests configured on this system."
    ::= { tFilterObjects 57 }

tFilterRPlcySNMPTestEntry OBJECT-TYPE
    SYNTAX      TFilterRPlcySNMPTestEntry
    MAX-ACCESS  not-accessible
    STATUS      current
    DESCRIPTION
        "The object tFilterRPlcySNMPTestEntry contains information
        about a specific SNMP test. Entries are created/deleted
        by user.
        The entry can be created only if the value of the object
        tFltrRPDstAddrType is ipv4(1).
        Entries have a presumed StorageType of nonVolatile."
    INDEX {
              tFilterRedirectPolicy,
              tFltrRPDstAddrType,
              tFltrRPDstAddr,
              tFltrRPSnmpTest
          }
    ::= { tFilterRPlcySNMPTestTable 1 }

TFilterRPlcySNMPTestEntry ::= SEQUENCE
    {
        tFltrRPSnmpTest                 TNamedItem,
        tFltrRPSnmpTLastChanged         TimeStamp,
        tFltrRPSnmpTRowStatus           RowStatus,
        tFltrRPSnmpTOID                 OBJECT IDENTIFIER,
        tFltrRPSnmpTCommunity           DisplayString,
        tFltrRPSnmpTSnmpVersion         INTEGER,
        tFltrRPSnmpTInterval            Unsigned32,
        tFltrRPSnmpTTimeout             Unsigned32,
        tFltrRPSnmpTDropCount           Unsigned32,
        tFltrRPSnmpTHoldDown            Unsigned32,
        tFltrRPSnmpTHoldDownRemain      Unsigned32,
        tFltrRPSnmpTLastActionTime      TimeStamp,
        tFltrRPSnmpTLastOID             OBJECT IDENTIFIER,
        tFltrRPSnmpTLastType            INTEGER,
        tFltrRPSnmpTLastCounter32Val    Counter32,
        tFltrRPSnmpTLastUnsigned32Val   Unsigned32,
        tFltrRPSnmpTLastTimeTicksVal    TimeTicks,
        tFltrRPSnmpTLastInt32Val        Integer32,
        tFltrRPSnmpTLastOctetStringVal  OCTET STRING,
        tFltrRPSnmpTLastIpAddressVal    IpAddress,
        tFltrRPSnmpTLastOidVal          OBJECT IDENTIFIER,
        tFltrRPSnmpTLastCounter64Val    Counter64,
        tFltrRPSnmpTLastOpaqueVal       Opaque,
        tFltrRPSnmpTLastAction          TmnxFilterRPlcyTestLastAction,
        tFltrRPSnmpTLastPrioChange      Integer32,
        tFltrRPSnmpTNextRespIndex       Integer32
    }

tFltrRPSnmpTest OBJECT-TYPE
    SYNTAX      TNamedItem
    MAX-ACCESS  not-accessible
    STATUS      current
    DESCRIPTION
        "The value of the object tFltrRPSnmpTest specifies the name
         of the SNMP test."
    ::= { tFilterRPlcySNMPTestEntry 1 }

tFltrRPSnmpTLastChanged OBJECT-TYPE
    SYNTAX      TimeStamp
    MAX-ACCESS  read-only
    STATUS      current
    DESCRIPTION
        "The value of the object tFltrRPSnmpTLastChanged indicates
        the timestamp of last change of this row in tFilterRPlcySNMPTestTable."
    ::= { tFilterRPlcySNMPTestEntry 2 }


tFltrRPSnmpTRowStatus OBJECT-TYPE
    SYNTAX      RowStatus
    MAX-ACCESS  read-create
    STATUS      current
    DESCRIPTION
        "The value of the object tFltrRPSnmpTRowStatus specifies the status
         of the conceptual row in tFilterRPlcySNMPTestTable.

         Rows can be created and destroyed by SNMP SET operations on this
         object."
    ::= { tFilterRPlcySNMPTestEntry 3 }

tFltrRPSnmpTOID OBJECT-TYPE
    SYNTAX      OBJECT IDENTIFIER
    MAX-ACCESS  read-create
    STATUS      current
    DESCRIPTION
        "The value of the object tFltrRPSnmpTOID specifies the OID of the
        object to be fetched from the destination.

        The value of this object can only be changed if the object
        tFltrRPSnmpTCommunity is changed at the same time."
    ::= { tFilterRPlcySNMPTestEntry 4 }

tFltrRPSnmpTCommunity OBJECT-TYPE
    SYNTAX      DisplayString (SIZE(0..32))
    MAX-ACCESS  read-create
    STATUS      current
    DESCRIPTION
        "The value of the object tFltrRPSnmpTCommunity specifies the SNMPv1
        or SNMPv2c Community String or the SNMPv3 Context Name used to conduct
        this SNMP test as described in RFC2571 and RFC2737.

        When the value of tFltrRPSnmpTSnmpVersion is 'snmpv1' or 'snmpv2c'
        this object represents a community string.  When the value of
        tFltrRPSnmpTSnmpVersion is 'snmpv3' this object represents a SNMPv3
        context name.
        The value of this object can only be changed if the object
        tFltrRPSnmpTOID is changed at the same time."
    DEFVAL { ''H }
    ::= { tFilterRPlcySNMPTestEntry 5 }

tFltrRPSnmpTSnmpVersion OBJECT-TYPE
    SYNTAX      INTEGER {
                     snmpv1 (1),
                     snmpv2c (2),
                     snmpv3 (3)
                 }
    MAX-ACCESS  read-create
    STATUS      current
    DESCRIPTION
        "The value of the object tFltrRPSnmpTSnmpVersion specifies the
        SNMP PDU format to be used while conducting the test. Currently
        only snmpv2c is supported."
    DEFVAL { snmpv2c }
    ::= { tFilterRPlcySNMPTestEntry 6 }

tFltrRPSnmpTInterval OBJECT-TYPE
    SYNTAX      Unsigned32 (1..60)
    UNITS        "seconds"
    MAX-ACCESS  read-create
    STATUS      current
    DESCRIPTION
        "The value of the object tFltrRPSnmpTInterval specifies the amount
        of time in seconds between consecutive requests sent to the far end
        host."
    DEFVAL { 1 }
    ::= { tFilterRPlcySNMPTestEntry 7 }

tFltrRPSnmpTTimeout OBJECT-TYPE
    SYNTAX      Unsigned32 (1..60)
    UNITS        "seconds"
    MAX-ACCESS  read-create
    STATUS      current
    DESCRIPTION
        "The value of the object tFltrRPSnmpTTimeout specifies the amount
        of time in seconds that is allowed for receiving a response from the
        far end host. If the response is not received within this time the
        far end host is considered unresponsive."
    DEFVAL { 1 }
    ::= { tFilterRPlcySNMPTestEntry 8 }

tFltrRPSnmpTDropCount OBJECT-TYPE
    SYNTAX      Unsigned32 (1..60)
    MAX-ACCESS  read-create
    STATUS      current
    DESCRIPTION
        "The value of the object tFltrRPSnmpTDropCount specifies the number of
        consecutive requests that must fail for the destination to be
        declared unreachable."
    DEFVAL { 3 }
    ::= { tFilterRPlcySNMPTestEntry 9 }

tFltrRPSnmpTHoldDown OBJECT-TYPE
    SYNTAX      Unsigned32 (0..86400)
    UNITS        "seconds"
    MAX-ACCESS  read-create
    STATUS      current
    DESCRIPTION
        "The value of the object tFltrRPSnmpTHoldDown specifies the amount
        of time in seconds that the system should be held down if this test
        has marked it unreachable."
    DEFVAL { 0 }
    ::= { tFilterRPlcySNMPTestEntry 10 }

tFltrRPSnmpTHoldDownRemain OBJECT-TYPE
    SYNTAX      Unsigned32 (0..86400)
    UNITS        "seconds"
    MAX-ACCESS  read-only
    STATUS      current
    DESCRIPTION
        "The value of the object tFltrRPSnmpTHoldDownRemain indicates the
        amount of time in seconds that the system will remain in held down
        state before being used again."
    ::= { tFilterRPlcySNMPTestEntry 11 }

tFltrRPSnmpTLastActionTime OBJECT-TYPE
    SYNTAX      TimeStamp
    MAX-ACCESS  read-only
    STATUS      current
    DESCRIPTION
        "The value of the object tFltrRPSnmpTLastActionTime indicates the
        time stamp when this test received a response for a probe sent out."
    ::= { tFilterRPlcySNMPTestEntry 12 }

tFltrRPSnmpTLastOID OBJECT-TYPE
    SYNTAX     OBJECT IDENTIFIER
    MAX-ACCESS read-only
    STATUS     current
    DESCRIPTION
        "The value of the object tFltrRPSnmpTLastOID indicates the OID
        received in the response."
    ::= { tFilterRPlcySNMPTestEntry 13 }

tFltrRPSnmpTLastType OBJECT-TYPE
    SYNTAX      INTEGER {  none(0),
                           counter32(1),
                           unsigned32(2),
                           timeTicks(3),
                           integer32(4),
                           ipAddress(5),
                           octetString(6),
                           objectId(7),
                           counter64(8),
                           opaque(9)
                        }
    MAX-ACCESS  read-only
    STATUS      current
    DESCRIPTION
        "The value of the object tFltrRPSnmpTLastType indicates the type
        of the last received SNMP object.

        Value none(0) indicates that no object was received.

        Value 'counter32' indicates that the value of SNMP object is of
        type Counter32.

        Value 'unsigned32' indicates that the value of SNMP object is of
        type Unsigned32.

        Value 'timeTicks' indicates that the value of SNMP object is of
        type timeTicks.

        Value 'integer32' indicates that the value of SNMP object is of
        type integer32.

        Value 'ipAddress' indicates that the value of SNMP object is of
        type ipAddress.

        Value 'octetString' indicates that the value of SNMP object is of
        type OCTET STRING.

        Value 'objectId' indicates that the value of SNMP object is of
        type OBJECT IDENTIFIER.

        Value 'counter64' indicates that the value of SNMP object is of
        type Counter64.

        Value 'unsigned32' indicates that the value of SNMP object is of
        type Unsigned32.

        Value 'opaque' indicates that the value of SNMP object is of
        type Opaque."
   ::= { tFilterRPlcySNMPTestEntry  14 }

tFltrRPSnmpTLastCounter32Val OBJECT-TYPE
    SYNTAX      Counter32
    MAX-ACCESS  read-only
    STATUS      current
    DESCRIPTION
        "The value of the object tFltrRPSnmpTLastCounter32Val indicates the
         value of an object received in the last test response, if the type of
         the received object is 'counter32'.
         When this object is set the value of the object tFltrRPSnmpTLastType
         is 'counter32'."
    ::= { tFilterRPlcySNMPTestEntry  15 }

tFltrRPSnmpTLastUnsigned32Val OBJECT-TYPE
    SYNTAX      Unsigned32
    MAX-ACCESS  read-only
    STATUS      current
    DESCRIPTION
        "The value of the object tFltrRPSnmpTLastUnsigned32Val indicates the
         value of an object received in the last test response, if the type of
         the received object is 'unsigned32'.
         When this object is set the value of the object tFltrRPSnmpTLastType
         is 'unsigned32'."
    ::= { tFilterRPlcySNMPTestEntry  16 }

tFltrRPSnmpTLastTimeTicksVal OBJECT-TYPE
    SYNTAX      TimeTicks
    MAX-ACCESS  read-only
    STATUS      current
    DESCRIPTION
        "The value of the object tFltrRPSnmpTLastTimeTicksVal indicates the
         value of an object received in the last test response, if the type of
         the received object is 'timeTicks'.
         When this object is set the value of the object tFltrRPSnmpTLastType
         is 'timeTicks'."
    ::= { tFilterRPlcySNMPTestEntry  17 }

tFltrRPSnmpTLastInt32Val OBJECT-TYPE
    SYNTAX      Integer32
    MAX-ACCESS  read-only
    STATUS      current
    DESCRIPTION
        "The value of the object tFltrRPSnmpTLastInt32Val indicates the
         value of an object received in the last test response, if the type of
         the received object is 'integer32'.
         When this object is set the value of the object tFltrRPSnmpTLastType
         is 'integer32'."
    ::= { tFilterRPlcySNMPTestEntry  18 }

tFltrRPSnmpTLastOctetStringVal OBJECT-TYPE
    SYNTAX      OCTET STRING (SIZE(0..255))
    MAX-ACCESS  read-only
    STATUS      current
    DESCRIPTION
        "The value of the object tFltrRPSnmpTLastOctetStringVal indicates the
         value of an object received in the last test response, if the type of
         the received object is 'octetString'.
         When this object is set the value of the object tFltrRPSnmpTLastType
         is 'octetString'."
    ::= { tFilterRPlcySNMPTestEntry  19 }

tFltrRPSnmpTLastIpAddressVal OBJECT-TYPE
    SYNTAX      IpAddress
    MAX-ACCESS  read-only
    STATUS      current
    DESCRIPTION
        "The value of the object tFltrRPSnmpTLastIpAddressVal indicates the
         value of an object received in the last test response, if the type of
         the received object is 'ipAddress'.
         When this object is set the value of the object tFltrRPSnmpTLastType
         is 'ipAddress'.

         This object is used only for IPv4 addresses. IPv6 addresses are
         represented using TAddress or InetAddress, and so the underlying
         datatype is OCTET STRING, and their value would be stored in the
         tFltrRPSnmpTLastOctetStringVal column."
    ::= { tFilterRPlcySNMPTestEntry  20 }

tFltrRPSnmpTLastOidVal OBJECT-TYPE
    SYNTAX      OBJECT IDENTIFIER
    MAX-ACCESS  read-only
    STATUS      current
    DESCRIPTION
        "The value of the object tFltrRPSnmpTLastOidVal indicates the
         value of an object received in the last test response, if the type of
         the received object is 'objectId'.
         When this object is set the value of the object tFltrRPSnmpTLastType
         is 'objectId'."
    ::= { tFilterRPlcySNMPTestEntry  21 }

tFltrRPSnmpTLastCounter64Val OBJECT-TYPE
    SYNTAX      Counter64
    MAX-ACCESS  read-only
    STATUS      current
    DESCRIPTION
        "The value of the object tFltrRPSnmpTLastCounter64Val indicates that
         the value of an object received in the last test response, if the type
         of the received object is 'counter64'.
         When this object is set the value of the object tFltrRPSnmpTLastType
         is 'counter64'."
    ::= { tFilterRPlcySNMPTestEntry  22 }

tFltrRPSnmpTLastOpaqueVal OBJECT-TYPE
    SYNTAX      Opaque (SIZE(0..255))
    MAX-ACCESS  read-only
    STATUS      current
    DESCRIPTION
        "The value of the object tFltrRPSnmpTLastOpaqueVal indicates the
         value of an object received in the last test response, if the type of
         the received object is 'opaque'.
         When this object is set the value of the object tFltrRPSnmpTLastType
         is 'opaque'."
    ::= { tFilterRPlcySNMPTestEntry  23 }

tFltrRPSnmpTLastAction OBJECT-TYPE
    SYNTAX      TmnxFilterRPlcyTestLastAction
    MAX-ACCESS  read-only
    STATUS      current
    DESCRIPTION
        "The value of the object tFltrRPSnmpTLastAction indicates
         an impact that the last test probe had on the value of the object
         tFltrRPDstOperState.

         If the value is 'disable', the destination may not be
         used for tFltrRPSnmpTHoldDown seconds."
    ::= { tFilterRPlcySNMPTestEntry 24 }

tFltrRPSnmpTLastPrioChange OBJECT-TYPE
    SYNTAX      Integer32 (-255..255)
    MAX-ACCESS  read-only
    STATUS      current
    DESCRIPTION
        "The value of the object tFltrRPSnmpTLastPrioChange indicates the
         priority change that the last test probe made to the operational
         priority of the destination. This object is significant only if
         the value of the object tFltrRPSnmpTLastAction is 'enable'.
         Otherwise it has no significance and it's holding the value '0'."
    ::= { tFilterRPlcySNMPTestEntry 25 }

tFltrRPSnmpTNextRespIndex OBJECT-TYPE
    SYNTAX      Integer32 (-1|1..2147483647)
    MAX-ACCESS  read-only
    STATUS      current
    DESCRIPTION
        "The value of the object tFltrRPSnmpTNextRespIndex indicates
        the next response index to be used while creating a row in the
        tFilterRPlcySNMPRespTable.

        The value of '-1' means that the maximum number of return values
        for this OID is already configured."
    ::= { tFilterRPlcySNMPTestEntry 26 }


--
-- Filter Redirect policy SNMP test response Table (IPv4/IPv6)
--
tFilterRPlcySNMPRespTableLastChg OBJECT-TYPE
    SYNTAX      TimeStamp
    MAX-ACCESS  read-only
    STATUS      current
    DESCRIPTION
        "The value of the object tFilterRPlcySNMPRespTableLastChg
         indicates the sysUpTime at the time of the last modification
         of tFilterRPlcySNMPRespTable.

         If no changes were made to the table since the last
         re-initialization of the local network management subsystem,
         then this object contains a zero value."
    ::= { tFilterObjects 58 }


tFilterRPlcySNMPRespTable OBJECT-TYPE
    SYNTAX      SEQUENCE OF TFilterRPlcySNMPRespEntry
    MAX-ACCESS  not-accessible
    STATUS      current
    DESCRIPTION
        "Each row in this table holds the effect of the test on the
        destination for a specific return value.

        Each row is created once and cannot be modified after creation.
        Any change attempts will be silently discarded."
    ::= { tFilterObjects 59 }

tFilterRPlcySNMPRespEntry OBJECT-TYPE
    SYNTAX      TFilterRPlcySNMPRespEntry
    MAX-ACCESS  not-accessible
    STATUS      current
    DESCRIPTION
        "Information about action to be taken for a specific destination
        when a specific response is received.

        Each row is created once and cannot be modified after creation.
        Any change attempts will be silently discarded."
    INDEX {
              tFilterRedirectPolicy,
              tFltrRPDstAddrType,
              tFltrRPDstAddr,
              tFltrRPSnmpTest,
              tFltrRPSnmpRspId
          }
    ::= { tFilterRPlcySNMPRespTable 1 }

TFilterRPlcySNMPRespEntry ::= SEQUENCE
    {
        tFltrRPSnmpRspId             Integer32,
        tFltrRPSnmpRspLastChanged    TimeStamp,
        tFltrRPSnmpRspRowStatus      RowStatus,
        tFltrRPSnmpRspAction         TmnxFilterRPlcyTestRespAction,
        tFltrRPSnmpRspPrioChange     Unsigned32,
        tFltrRPSnmpRspOID            OBJECT IDENTIFIER,
        tFltrRPSnmpRspType           INTEGER,
        tFltrRPSnmpRspCounter32Val   Counter32,
        tFltrRPSnmpRspUnsigned32Val  Unsigned32,
        tFltrRPSnmpRspTimeTicksVal   TimeTicks,
        tFltrRPSnmpRspInt32Val       Integer32,
        tFltrRPSnmpRspOctetStringVal OCTET STRING,
        tFltrRPSnmpRspIpAddressVal   IpAddress,
        tFltrRPSnmpRspOidVal         OBJECT IDENTIFIER,
        tFltrRPSnmpRspCounter64Val   Counter64,
        tFltrRPSnmpRspOpaqueVal      Opaque
    }

tFltrRPSnmpRspId OBJECT-TYPE
    SYNTAX      Integer32 (1..2147483647)
    MAX-ACCESS  not-accessible
    STATUS      current
    DESCRIPTION
        "The value of the object tFltrRPSnmpRspId indicates the ID of the
        response entry."
    ::= { tFilterRPlcySNMPRespEntry 1 }

tFltrRPSnmpRspLastChanged OBJECT-TYPE
    SYNTAX      TimeStamp
    MAX-ACCESS  read-only
    STATUS      current
    DESCRIPTION
        "The value of the object tFltrRPSnmpRspLastChanged indicates
        the timestamp of last change of this row in tFilterRPlcySNMPRespTable."
    ::= { tFilterRPlcySNMPRespEntry 2 }


tFltrRPSnmpRspRowStatus OBJECT-TYPE
    SYNTAX      RowStatus
    MAX-ACCESS  read-create
    STATUS      current
    DESCRIPTION
        "The value of the object tFltrRPSnmpRspRowStatus specifies the status
         of the conceptual row in tFilterRPlcySNMPRespTable.

         Rows can be created and destroyed by SNMP SET operations on this
         object."
    ::= { tFilterRPlcySNMPRespEntry 3 }

tFltrRPSnmpRspAction OBJECT-TYPE
    SYNTAX      TmnxFilterRPlcyTestRespAction
    MAX-ACCESS  read-create
    STATUS      current
    DESCRIPTION
        "The value of the object tFltrRPSnmpRspAction specifies the action
        which will be taken on the operational priority of a destination
        (tFilterRDOperPriority), if the received object OID and value matches
        the values defined in TFilterRPlcySNMPRespEntry.

        If tFltrRPSnmpRspPrioChange is 0 the value of this object will be
        set to 'disable'.

        This object cannot be modified after creation. Any change attempts
        will be silently discarded."
    DEFVAL { disable }
    ::= { tFilterRPlcySNMPRespEntry 4 }

tFltrRPSnmpRspPrioChange OBJECT-TYPE
    SYNTAX      Unsigned32 (0..255)
    MAX-ACCESS  read-create
    STATUS      current
    DESCRIPTION
        "The value of the object tFltrRPSnmpRspPrioChange specifies
        the offset to be applied to the destination base priority
        (tFilterRDAdminPriority) in order to compute the tFilterRDOperPriority
        as a result of this test, if the tFltrRPSnmpRspAction is either
        'increase' or 'decrease'.

        If tFltrRPSnmpRspAction is 'disable', tFltrRPSnmpRspPrioChange will
        be forced to 0. Any change to tFltrRPSnmpRspPrioChange will be
        silently discarded in this case.

        Setting the object tFltrRPSnmpRspPrioChange to 0 will cause the value of
        tFltrRPSnmpRspAction to be set to 'disable'.

        This object cannot be modified after creation. Any change attempts
        will be silently discarded."
    DEFVAL { 0 }
    ::= { tFilterRPlcySNMPRespEntry 5 }

tFltrRPSnmpRspOID OBJECT-TYPE
    SYNTAX     OBJECT IDENTIFIER
    MAX-ACCESS read-create
    STATUS     current
    DESCRIPTION
        "The value of the object tFltrRPSnmpRspOID specifies the OID to be
        received in the response.

        This field cannot be modified after creation. Any change attempts
        will be silently discarded."
    ::= { tFilterRPlcySNMPRespEntry 6 }

tFltrRPSnmpRspType OBJECT-TYPE
    SYNTAX      INTEGER {  counter32(1),
                           unsigned32(2),
                           timeTicks(3),
                           integer32(4),
                           ipAddress(5),
                           octetString(6),
                           objectId(7),
                           counter64(8),
                           opaque(9)
                        }
    MAX-ACCESS  read-create
    STATUS      current
    DESCRIPTION
       "The value of the object tFltrRPSnmpRspType specifies the type of
        the SNMP object to be received.

        Note: types 'objectId' and 'counter64' are not supported
        for now, and will be rejected when used.

        This object cannot be modified after creation. Any change attempts
        will be silently discarded.

        Value 'counter32' indicates that the value of SNMP object is of
        type Counter32.

        Value 'unsigned32' indicates that the value of SNMP object is of
        type Unsigned32.

        Value 'timeTicks' indicates that the value of SNMP object is of
        type timeTicks.

        Value 'integer32' indicates that the value of SNMP object is of
        type integer32.

        Value 'ipAddress' indicates that the value of SNMP object is of
        type ipAddress.

        Value 'octetString' indicates that the value of SNMP object is of
        type OCTET STRING.

        Value 'objectId' indicates that the value of SNMP object is of
        type OBJECT IDENTIFIER.

        Value 'counter64' indicates that the value of SNMP object is of
        type Counter64.

        Value 'unsigned32' indicates that the value of SNMP object is of
        type Unsigned32.

        Value 'opaque' indicates that the value of SNMP object is of
        type Opaque."
    ::= { tFilterRPlcySNMPRespEntry  7 }

tFltrRPSnmpRspCounter32Val OBJECT-TYPE
    SYNTAX      Counter32
    MAX-ACCESS  read-create
    STATUS      current
    DESCRIPTION
       "The value of the object tFltrRPSnmpRspCounter32Val specifies the value
        of type Counter32 which the object received in the test response
        should have in order to pass the test.

        When this value is specified the value of the object tFltrRPSnmpRspType
        should be set to 'counter32'.

        This field cannot be modified after creation. Any change attempts
        will be silently discarded."
    ::= { tFilterRPlcySNMPRespEntry  8 }

tFltrRPSnmpRspUnsigned32Val OBJECT-TYPE
    SYNTAX      Unsigned32
    MAX-ACCESS  read-create
    STATUS      current
    DESCRIPTION
       "The value of the object tFltrRPSnmpRspUnsigned32Val specifies the value
        of type Unsigned32 which the object received in the test response
        should have in order to pass the test.

        When this value is specified the value of the object tFltrRPSnmpRspType
        should be set to 'unsigned32'.

        This field cannot be modified after creation. Any change attempts
        will be silently discarded."
    ::= { tFilterRPlcySNMPRespEntry  9 }

tFltrRPSnmpRspTimeTicksVal OBJECT-TYPE
    SYNTAX      TimeTicks
    MAX-ACCESS  read-create
    STATUS      current
    DESCRIPTION
       "The value of the object tFltrRPSnmpRspTimeTicksVal specifies the value
        of type TimeTicks which the object received in the test response
        should have in order to pass the test.

        When this value is specified the value of the object tFltrRPSnmpRspType
        should be set to 'timeTicks'.

        This field cannot be modified after creation. Any change attempts
        will be silently discarded."
    ::= { tFilterRPlcySNMPRespEntry  10 }

tFltrRPSnmpRspInt32Val OBJECT-TYPE
    SYNTAX      Integer32
    MAX-ACCESS  read-create
    STATUS      current
    DESCRIPTION
       "The value of the object tFltrRPSnmpRspInt32Val specifies the value
        of type Integer32 which the object received in the test response
        should have in order to pass the test.

        When this value is specified the value of the object tFltrRPSnmpRspType
        should be set to 'integer32'.

        This field cannot be modified after creation. Any change attempts
        will be silently discarded."
    ::= { tFilterRPlcySNMPRespEntry  11 }

tFltrRPSnmpRspOctetStringVal OBJECT-TYPE
    SYNTAX      OCTET STRING (SIZE(0..255))
    MAX-ACCESS  read-create
    STATUS      current
    DESCRIPTION
       "The value of the object tFltrRPSnmpRspOctetStringVal specifies the value
        of type OCTET STRING which the object received in the test response
        should have in order to pass the test.

        When this value is specified the value of the object tFltrRPSnmpRspType
        should be set to 'octetString'.

        This field cannot be modified after creation. Any change attempts
        will be silently discarded."
    ::= { tFilterRPlcySNMPRespEntry  12 }

tFltrRPSnmpRspIpAddressVal OBJECT-TYPE
    SYNTAX      IpAddress
    MAX-ACCESS  read-create
    STATUS      current
    DESCRIPTION
       "The value of the object tFltrRPSnmpRspIpAddressVal specifies the  IPv4
        address which the object received in the test response should have
        in order to pass the test.

        When this value is specified the value of the object tFltrRPSnmpRspType
        should be set to 'ipAddress'.

        IPv6 addresses are represented using TAddress or InetAddress,
        and so the underlying data type is OCTET STRING, and their
        value would be stored in the tFltrRPSnmpRspOctetStringVal
        column.

        This field cannot be modified after creation. Any change attempts
        will be silently discarded."
    ::= { tFilterRPlcySNMPRespEntry  13 }

tFltrRPSnmpRspOidVal OBJECT-TYPE
    SYNTAX      OBJECT IDENTIFIER
    MAX-ACCESS  read-create
    STATUS      current
    DESCRIPTION
       "The value of the object tFltrRPSnmpRspOidVal specifies the OID
        which the object received in the test response should have in order
        to pass the test.

        When this value is specified the value of the object tFltrRPSnmpRspType
        should be set to 'objectId'.

        This field cannot be modified after creation. Any change attempts
        will be silently discarded."
    ::= { tFilterRPlcySNMPRespEntry  14 }

tFltrRPSnmpRspCounter64Val OBJECT-TYPE
    SYNTAX      Counter64
    MAX-ACCESS  read-create
    STATUS      current
    DESCRIPTION
       "The value of the object tFltrRPSnmpRspCounter64Val specifies the value
        of type Counter64 which the object received in the test response should
        have in order to pass the test.

        When this value is specified the value of the object tFltrRPSnmpRspType
        should be set to 'counter64'.

        This field cannot be modified after creation. Any change attempts
        will be silently discarded."
    ::= { tFilterRPlcySNMPRespEntry  15 }

tFltrRPSnmpRspOpaqueVal OBJECT-TYPE
    SYNTAX      Opaque (SIZE(0..255))
    MAX-ACCESS  read-create
    STATUS      current
    DESCRIPTION
       "The value of the object tFltrRPSnmpRspOpaqueVal specifies the value
        of type Opaque which the object received in the test response should
        have in order to pass the test.

        When this value is specified the value of the object tFltrRPSnmpRspType
        should be set to 'opaque'.

        This field cannot be modified after creation. Any change attempts
        will be silently discarded."
    ::= { tFilterRPlcySNMPRespEntry  16 }


--
-- Filter Redirect URL Test Table (IPv4/IPv6)
--
tFilterRPlcyURLTestTableLastChg OBJECT-TYPE
    SYNTAX      TimeStamp
    MAX-ACCESS  read-only
    STATUS      current
    DESCRIPTION
        "The value of the object tFilterRPlcyURLTestTableLastChg
         indicates the sysUpTime at the time of the last modification
         of tFilterRPlcyURLTestTable.

         If no changes were made to the table since the last
         re-initialization of the local network management subsystem,
         then this object contains a zero value."
    ::= { tFilterObjects 60 }


tFilterRPlcyURLTestTable OBJECT-TYPE
    SYNTAX      SEQUENCE OF TFilterRPlcyURLTestEntry
    MAX-ACCESS  not-accessible
    STATUS      current
    DESCRIPTION
        "This table contains a list of all redirect URL tests configured on this
        system."
    ::= { tFilterObjects 61 }

tFilterRPlcyURLTestEntry OBJECT-TYPE
    SYNTAX      TFilterRPlcyURLTestEntry
    MAX-ACCESS  not-accessible
    STATUS      current
    DESCRIPTION
        "Information about a specific URL test configured for a destination.
        Entries are created/deleted  by user.
        The entry can be created only if the value of the object
        tFltrRPDstAddrType is ipv4(1).
        Entries have a presumed StorageType of nonVolatile."
    INDEX {
              tFilterRedirectPolicy,
              tFltrRPDstAddrType,
              tFltrRPDstAddr,
              tFltrRPUrlTest
          }
    ::= { tFilterRPlcyURLTestTable 1 }

TFilterRPlcyURLTestEntry ::= SEQUENCE
    {
        tFltrRPUrlTest             TNamedItem,
        tFltrRPUrlTLastChanged     TimeStamp,
        tFltrRPUrlTRowStatus       RowStatus,
        tFltrRPUrlTUrl             DisplayString,
        tFltrRPUrlTHttpVersion     DisplayString,
        tFltrRPUrlTInterval        Unsigned32,
        tFltrRPUrlTTimeout         Unsigned32,
        tFltrRPUrlTDropCount       Unsigned32,
        tFltrRPUrlTHoldDown        Unsigned32,
        tFltrRPUrlTHoldDownRemain  Unsigned32,
        tFltrRPUrlTLastActionTime  TimeStamp,
        tFltrRPUrlTLastRetCode     Unsigned32,
        tFltrRPUrlTLastAction      TmnxFilterRPlcyTestLastAction,
        tFltrRPUrlTLastPrioChange  Integer32
    }

tFltrRPUrlTest OBJECT-TYPE
    SYNTAX      TNamedItem
    MAX-ACCESS  not-accessible
    STATUS      current
    DESCRIPTION
        "The value of the object tFltrRPUrlTest specifies the name of the
        URL test."
    ::= { tFilterRPlcyURLTestEntry 1 }

tFltrRPUrlTLastChanged OBJECT-TYPE
    SYNTAX      TimeStamp
    MAX-ACCESS  read-only
    STATUS      current
    DESCRIPTION
        "The value of the object tFltrRPUrlTLastChanged indicates
        the timestamp of last change of this row in tFilterRPlcyURLTestTable."
    ::= { tFilterRPlcyURLTestEntry 2 }

tFltrRPUrlTRowStatus OBJECT-TYPE
    SYNTAX      RowStatus
    MAX-ACCESS  read-create
    STATUS      current
    DESCRIPTION
       "The value of the object tFltrRPUrlTRowStatus specifies the status
        of the conceptual row in tFilterRPlcyURLTestTable.

        Rows in tFilterRPlcyURLTestTable can be created and destroyed by
        SNMP SET operations on this object."
    ::= { tFilterRPlcyURLTestEntry 3 }

tFltrRPUrlTUrl OBJECT-TYPE
    SYNTAX      DisplayString
    MAX-ACCESS  read-create
    STATUS      current
    DESCRIPTION
        "The value of the object tFltrRPUrlTUrl specifies the URL to be probed."
    DEFVAL { ''H }
    ::= { tFilterRPlcyURLTestEntry 4 }

tFltrRPUrlTHttpVersion OBJECT-TYPE
    SYNTAX      DisplayString
    MAX-ACCESS  read-create
    STATUS      current
    DESCRIPTION
        "The value of the object tFltrRPUrlTHttpVersion specifies HTTP Version
        to be used while performing the URL test.
        The system by default uses HTTP Version 1.1 until explicitly
        specified."
    DEFVAL { "1.1" }
    ::= { tFilterRPlcyURLTestEntry 5 }

tFltrRPUrlTInterval OBJECT-TYPE
    SYNTAX      Unsigned32 (1..60)
    UNITS        "seconds"
    MAX-ACCESS  read-create
    STATUS      current
    DESCRIPTION
       "The value of the object tFltrRPUrlTInterval specifies the amount
        of time in seconds between consecutive requests sent to the far end
        host."
    DEFVAL { 1 }
    ::= { tFilterRPlcyURLTestEntry 6 }

tFltrRPUrlTTimeout OBJECT-TYPE
    SYNTAX      Unsigned32 (1..60)
    UNITS        "seconds"
    MAX-ACCESS  read-create
    STATUS      current
    DESCRIPTION
       "The value of the object tFltrRPUrlTTimeout specifies the amount
        of time in seconds that is allowed for receiving a response
        from the far end host. If the response is not received within this
        time the far end host is considered unresponsive."
    DEFVAL { 1 }
    ::= { tFilterRPlcyURLTestEntry 7 }

tFltrRPUrlTDropCount OBJECT-TYPE
    SYNTAX      Unsigned32 (1..60)
    MAX-ACCESS  read-create
    STATUS      current
    DESCRIPTION
        "The value of the object tFltrRPUrlTDropCount specifies the number
        of consecutive requests that must fail for the destination to be
        declared unreachable."
    DEFVAL { 3 }
    ::= { tFilterRPlcyURLTestEntry 8 }

tFltrRPUrlTHoldDown OBJECT-TYPE
    SYNTAX      Unsigned32 (0..86400)
    UNITS        "seconds"
    MAX-ACCESS  read-create
    STATUS      current
    DESCRIPTION
       "The value of the object tFltrRPUrlTHoldDown specifies the amount of
        time in seconds that the system should be held down this test has
        marked it unreachable."
    DEFVAL { 0 }
    ::= { tFilterRPlcyURLTestEntry 9 }

tFltrRPUrlTHoldDownRemain OBJECT-TYPE
    SYNTAX      Unsigned32 (0..86400)
    UNITS        "seconds"
    MAX-ACCESS  read-only
    STATUS      current
    DESCRIPTION
       "The value of the object tFltrRPUrlTHoldDownRemain indicates the amount
        of time in seconds that the system will remain in held down state before
        being used again."
    ::= { tFilterRPlcyURLTestEntry 10 }

tFltrRPUrlTLastActionTime OBJECT-TYPE
    SYNTAX      TimeStamp
    MAX-ACCESS  read-only
    STATUS      current
    DESCRIPTION
        "The value of the object tFltrRPUrlTLastActionTime indicates the
        time stamp when this test received a response for a probe sent out."
    ::= { tFilterRPlcyURLTestEntry 11 }

tFltrRPUrlTLastRetCode OBJECT-TYPE
    SYNTAX      Unsigned32
    MAX-ACCESS  read-only
    STATUS      current
    DESCRIPTION
        "The value of the object tFltrRPUrlTLastRetCode indicates the return
        code received in the last response."
    ::= { tFilterRPlcyURLTestEntry 12 }

tFltrRPUrlTLastAction OBJECT-TYPE
    SYNTAX      TmnxFilterRPlcyTestLastAction
    MAX-ACCESS  read-only
    STATUS      current
    DESCRIPTION
        "The value of the object tFltrRPUrlTLastAction indicates impact that
        the last test probe had on the operational status of the destination
        as maintained in tFilterRDOperState.

        If the last action was 'disable', the destination may not be
        used for tFltrRPUrlTHoldDown seconds."
    ::= { tFilterRPlcyURLTestEntry 13 }

tFltrRPUrlTLastPrioChange OBJECT-TYPE
    SYNTAX      Integer32 (-255..255)
    MAX-ACCESS  read-only
    STATUS      current
    DESCRIPTION
        "The value of the object tFltrRPUrlTLastPrioChange indicates the
        priority change that the last test probe made to the operational
        priority of the destination. This object is significant only if
        the value of the object tFltrRPUrlTLastAction is 'enable'.
        Otherwise it has no significance and it's holding the value '0'."
    ::= { tFilterRPlcyURLTestEntry 14 }


--
-- Filter Redirect URL Response Table (IPv4/IPv6)
--
tFilterRPlcyURLRespTableLastChg OBJECT-TYPE
    SYNTAX      TimeStamp
    MAX-ACCESS  read-only
    STATUS      current
    DESCRIPTION
        "The value of the object tFilterRPlcyURLRespTableLastChg
         indicates the sysUpTime at the time of the last modification
         of tFilterRPlcyURLRespTable.

         If no changes were made to the table since the last
         re-initialization of the local network management subsystem,
         then this object contains a zero value."
    ::= { tFilterObjects 62 }


tFilterRPlcyURLRespTable OBJECT-TYPE
    SYNTAX      SEQUENCE OF TFilterRPlcyURLRespEntry
    MAX-ACCESS  not-accessible
    STATUS      current
    DESCRIPTION
       "Each row in this table specifies the effect of the test on
       the destination for a range of return values."
    ::= { tFilterObjects 63 }

tFilterRPlcyURLRespEntry OBJECT-TYPE
    SYNTAX      TFilterRPlcyURLRespEntry
    MAX-ACCESS  not-accessible
    STATUS      current
    DESCRIPTION
       "Entry contains information about an action to be taken for a specific
       destination when a return value within the range specifies by
       tFltrRPUrlTRspLowRspCode and tFltrRPUrlTRspHighRspCode is received."
    INDEX {
              tFilterRedirectPolicy,
              tFltrRPDstAddrType,
              tFltrRPDstAddr,
              tFltrRPUrlTest,
              tFltrRPUrlTRspLowRspCode,
              tFltrRPUrlTRspHighRspCode
          }
    ::= { tFilterRPlcyURLRespTable 1 }

TFilterRPlcyURLRespEntry ::= SEQUENCE
    {
        tFltrRPUrlTRspLowRspCode       Unsigned32,
        tFltrRPUrlTRspHighRspCode      Unsigned32,
        tFltrRPUrlTRspLastChanged      TimeStamp,
        tFltrRPUrlTRspRowStatus        RowStatus,
        tFltrRPUrlTRspAction           TmnxFilterRPlcyTestRespAction,
        tFltrRPUrlTRspPrioChange       Unsigned32
    }

tFltrRPUrlTRspLowRspCode OBJECT-TYPE
    SYNTAX      Unsigned32
    MAX-ACCESS  not-accessible
    STATUS      current
    DESCRIPTION
        "The value of the object tFltrRPUrlTRspLowRspCode specifies
        the lower return code of the range specified by this entry."
    ::= { tFilterRPlcyURLRespEntry 1 }

tFltrRPUrlTRspHighRspCode OBJECT-TYPE
    SYNTAX      Unsigned32
    MAX-ACCESS  not-accessible
    STATUS      current
    DESCRIPTION
        "The value of the object tFltrRPUrlTRspHighRspCode specifies
        the higher return code of the range specified by this entry."
    ::= { tFilterRPlcyURLRespEntry 2 }

tFltrRPUrlTRspLastChanged OBJECT-TYPE
    SYNTAX      TimeStamp
    MAX-ACCESS  read-only
    STATUS      current
    DESCRIPTION
        "The value of the object tFltrRPUrlTRspLastChanged indicates
        the timestamp of last change of this row in tFilterRPlcyURLRespTable."
    ::= { tFilterRPlcyURLRespEntry 3 }

tFltrRPUrlTRspRowStatus OBJECT-TYPE
    SYNTAX      RowStatus
    MAX-ACCESS  read-create
    STATUS      current
    DESCRIPTION
         "The value of the object tFltrRPUrlTRspRowStatus specifies the status
         of the conceptual row in tFilterRPlcyURLRespTable.

         Rows can be created and destroyed by SNMP SET operations on this
         object."
    ::= { tFilterRPlcyURLRespEntry 4 }

tFltrRPUrlTRspAction OBJECT-TYPE
    SYNTAX     TmnxFilterRPlcyTestRespAction
    MAX-ACCESS  read-create
    STATUS      current
    DESCRIPTION
       "The value of the object tFltrRPUrlTRspAction specifies the action
        which will be taken on the operational priority of a
        destination (tFilterRDOperPriority), if the received object OID and
        value matches the values defined in TFilterRPlcySNMPRespEntry.

        If tFltrRPUrlTRspPrioChange is 0 the value of this object will be
        set to 'disable'."
    DEFVAL { disable }
    ::= { tFilterRPlcyURLRespEntry 5 }

tFltrRPUrlTRspPrioChange OBJECT-TYPE
    SYNTAX      Unsigned32 (0..255)
    MAX-ACCESS  read-create
    STATUS      current
    DESCRIPTION
        "If the tFltrRPUrlTRspAction is either 'increase' or 'decrease',
        the value of the object tFltrRPUrlTRspPrioChange specifies
        the offset to be applied to the destination base priority
        (tFilterRDAdminPriority) in order to compute the tFilterRDOperPriority
        as a result of this test.

        If tFltrRPUrlTRspAction is 'disable', tFltrRPUrlTRspPrioChange will
        be forced to 0. Any change to tFltrRPUrlTRspPrioChange will be
        silently discarded in this case.

        Setting the object tFltrRPUrlTRspPrioChange to 0 will cause the value
        of tFltrRPUrlTRspAction to be set to 'disable'."
    DEFVAL { 0 }
    ::= { tFilterRPlcyURLRespEntry 6 }


--
-- Filter Redirect Policy Ping Test Table (IPv4/IPv6)
--
tFilterRPlcyPingTestTableLastChg OBJECT-TYPE
    SYNTAX      TimeStamp
    MAX-ACCESS  read-only
    STATUS      current
    DESCRIPTION
        "The value of the object tFilterRPlcyPingTestTableLastChg
         indicates the sysUpTime at the time of the last modification
         of tFilterRPlcyPingTestTable.

         If no changes were made to the table since the last
         re-initialization of the local network management subsystem,
         then this object contains a zero value."
    ::= { tFilterObjects 64 }

tFilterRPlcyPingTestTable OBJECT-TYPE
    SYNTAX      SEQUENCE OF TFilterRPlcyPingTestEntry
    MAX-ACCESS  not-accessible
    STATUS      current
    DESCRIPTION
        "The table tFilterRPlcyPingTestTable contains a list of all redirect
        Ping tests configured on this system."
    ::= { tFilterObjects 65 }

tFilterRPlcyPingTestEntry OBJECT-TYPE
    SYNTAX      TFilterRPlcyPingTestEntry
    MAX-ACCESS  not-accessible
    STATUS      current
    DESCRIPTION
        "Entry contains information about a specific Ping test.
        Entries are created/deleted by user and have a presumed
        StorageType of nonVolatile."
    INDEX {
              tFilterRedirectPolicy,
              tFltrRPDstAddrType,
              tFltrRPDstAddr
          }
    ::= { tFilterRPlcyPingTestTable 1 }

TFilterRPlcyPingTestEntry ::= SEQUENCE
    {
        tFltrRPPingTLastChanged     TimeStamp,
        tFltrRPPingTRowStatus       RowStatus,
        tFltrRPPingTInterval        Unsigned32,
        tFltrRPPingTTimeout         Unsigned32,
        tFltrRPPingTDropCount       Unsigned32,
        tFltrRPPingTHoldDown        Unsigned32,
        tFltrRPPingTHoldDownRemain  Unsigned32,
        tFltrRPPingTLastActionTime  TimeStamp,
        tFltrRPPingTLastAction      TmnxFilterRPlcyTestLastAction
    }

tFltrRPPingTLastChanged OBJECT-TYPE
    SYNTAX      TimeStamp
    MAX-ACCESS  read-only
    STATUS      current
    DESCRIPTION
        "The value of the object tFltrRPPingTLastChanged indicates
        the timestamp of last change of this row in tFilterRPlcyPingTestTable."
    ::= { tFilterRPlcyPingTestEntry 1 }

tFltrRPPingTRowStatus OBJECT-TYPE
    SYNTAX      RowStatus
    MAX-ACCESS  read-create
    STATUS      current
    DESCRIPTION
        "The value of the object tFltrRPPingTRowStatus specifies the status
         of the conceptual row in tFilterRPlcyPingTestTable.

         Rows are created and destroyed by SNMP SET operations on this
         object."
    ::= { tFilterRPlcyPingTestEntry 2 }

tFltrRPPingTInterval OBJECT-TYPE
    SYNTAX      Unsigned32 (1..60)
    UNITS        "seconds"
    MAX-ACCESS  read-create
    STATUS      current
    DESCRIPTION
        "The value of the object tFltrRPPingTInterval specifies the amount
        of time in seconds between consecutive requests sent to the far end
        host.

        Note that the value of tFltrRPPingTInterval can only be modified if the
        value of the corresponding tFilterRPAdminState and/or
        tFltrRPDstAdminState object is outOfService."
    DEFVAL { 1 }
    ::= { tFilterRPlcyPingTestEntry 3 }

tFltrRPPingTTimeout OBJECT-TYPE
    SYNTAX      Unsigned32 (1..60)
    UNITS        "seconds"
    MAX-ACCESS  read-create
    STATUS      current
    DESCRIPTION
        "The value of the object tFltrRPPingTTimeout specifies the amount of
        time in seconds that is allowed for receiving a response from the far
        end host. If a reply is not received within this time the far end host
        is considered unresponsive.

        Note that the value of tFltrRPPingTTimeout can only be modified if the
        value of the corresponding tFilterRPAdminState and/or
        tFltrRPDstAdminState object is outOfService."
    DEFVAL { 1 }
    ::= { tFilterRPlcyPingTestEntry 4 }

tFltrRPPingTDropCount OBJECT-TYPE
    SYNTAX      Unsigned32 (1..60)
    MAX-ACCESS  read-create
    STATUS      current
    DESCRIPTION
        "The value of the object tFltrRPPingTDropCount specifies the number of
        consecutive requests that must fail for the destination to be
        declared unreachable."
    DEFVAL { 3 }
    ::= { tFilterRPlcyPingTestEntry 5 }

tFltrRPPingTHoldDown OBJECT-TYPE
    SYNTAX      Unsigned32 (0..86400)
    UNITS        "seconds"
    MAX-ACCESS  read-create
    STATUS      current
    DESCRIPTION
        "The value of the object tFltrRPPingTHoldDown specifies the amount of
        time in seconds that the system should be held down if any of the test
        has marked it unreachable."
    DEFVAL { 0 }
    ::= { tFilterRPlcyPingTestEntry 6 }

tFltrRPPingTHoldDownRemain OBJECT-TYPE
    SYNTAX      Unsigned32 (0..86400)
    UNITS        "seconds"
    MAX-ACCESS  read-only
    STATUS      current
    DESCRIPTION
        "The value of the object tFltrRPPingTHoldDownRemain indicates the amount
        of time in seconds that the system will remain in held down state before
        being used again."
    ::= { tFilterRPlcyPingTestEntry 7 }

tFltrRPPingTLastActionTime OBJECT-TYPE
    SYNTAX      TimeStamp
    MAX-ACCESS  read-only
    STATUS      current
    DESCRIPTION
        "The value of the object tFltrRPPingTLastActionTime maintains the time
        stamp when this test received a response for a probe sent out."
    ::= { tFilterRPlcyPingTestEntry 8 }

tFltrRPPingTLastAction OBJECT-TYPE
    SYNTAX      TmnxFilterRPlcyTestLastAction
    MAX-ACCESS  read-only
    STATUS      current
    DESCRIPTION
        "The value of the object tFltrRPPingTLastAction maintains impact that
        the last test probe made on the operational status of the destination
        as maintained in tFltrRPDstOperState.

        If the last action was 'disable', the destination may not be
        used for tFilterRPTHoldDown seconds."
    ::= { tFilterRPlcyPingTestEntry 9 }

--
-- Filter Redirect Policy Unicast Route Reachability test table
--
tFilterRPlcyUcastRtTTableLastChg OBJECT-TYPE
    SYNTAX      TimeStamp
    MAX-ACCESS  read-only
    STATUS      current
    DESCRIPTION
        "The value of the object tFilterRPlcyUcastRtTTableLastChg
         indicates the sysUpTime at the time of the last modification
         of tFilterRPlcyUnicastRtTestTable.

         If no changes were made to the table since the last
         re-initialization of the local network management subsystem,
         then this object contains a zero value."
    ::= { tFilterObjects 66 }


tFilterRPlcyUnicastRtTestTable OBJECT-TYPE
    SYNTAX      SEQUENCE OF TFilterRPlcyUnicastRtTestEntry
    MAX-ACCESS  not-accessible
    STATUS      current
    DESCRIPTION
        "The table tFilterRPlcyUnicastRtTestTable contains list of all
         Unicast Route Reachability tests configured on this system."
    ::= { tFilterObjects 67 }

tFilterRPlcyUnicastRtTestEntry OBJECT-TYPE
    SYNTAX      TFilterRPlcyUnicastRtTestEntry
    MAX-ACCESS  not-accessible
    STATUS      current
    DESCRIPTION
        "Entry contains information about a specific Unicast Route Reachability
         test configured for a destination in a Redirect Policy.

         There can be only one Unicast Route Reachability test configured
         per destination.

         Upon creation of the entry the IP address of the destination specified
         by the values of the objects tFltrRPDstAddrType and tFltrRPDstAddr
         and optionally (if not equal to the default value) the virtual router
         instance ID specified by the value of the object tFilterRPVrtrId
         is registered with RTM module.

         Redirect policy is then informed about any change of the reachability
         of the destination (based on availability of a route in a particular
         routing table) and modifies the value of the object
         tFltrRPDstOperState accordingly.

         An entry in the table tFilterRPlcyUnicastRtTestTable is created and
         destroyed by SNMP SET operations on the object
         tFltrRPUcastRtTRowStatus."
    INDEX {
              tFilterRedirectPolicy,
              tFltrRPDstAddrType,
              tFltrRPDstAddr
          }
    ::= { tFilterRPlcyUnicastRtTestTable 1 }

TFilterRPlcyUnicastRtTestEntry ::= SEQUENCE
    {
        tFltrRPUcastRtTLastChanged    TimeStamp,
        tFltrRPUcastRtTRowStatus      RowStatus,
        tFltrRPUcastRtTLastActionTime TimeStamp,
        tFltrRPUcastRtTLastAction     TmnxFilterRPlcyTestLastAction
    }

tFltrRPUcastRtTLastChanged OBJECT-TYPE
    SYNTAX      TimeStamp
    MAX-ACCESS  read-only
    STATUS      current
    DESCRIPTION
        "The value of the object tFltrRPUcastRtTLastChanged indicates
        the timestamp of last change of this row in
        tFilterRPlcyUnicastRtTestTable."
    ::= { tFilterRPlcyUnicastRtTestEntry 1 }


tFltrRPUcastRtTRowStatus OBJECT-TYPE
    SYNTAX      RowStatus
    MAX-ACCESS  read-create
    STATUS      current
    DESCRIPTION
        "The value of the object tFltrRPUcastRtTRowStatus specifies the status
         of the conceptual row in tFilterRPlcyUnicastRtTestTable.

         Rows are created and destroyed by SNMP SET operations on this
         object."
    ::= { tFilterRPlcyUnicastRtTestEntry 2 }

tFltrRPUcastRtTLastActionTime OBJECT-TYPE
    SYNTAX      TimeStamp
    MAX-ACCESS  read-only
    STATUS      current
    DESCRIPTION
        "The value of the object tFltrRPUcastRtTLastActionTime indicates
         the time stamp when the last update from RTM module
         for this destination was received."
    ::= { tFilterRPlcyUnicastRtTestEntry 3 }

tFltrRPUcastRtTLastAction OBJECT-TYPE
    SYNTAX      TmnxFilterRPlcyTestLastAction
    MAX-ACCESS  read-only
    STATUS      current
    DESCRIPTION
        "The value of the object tFltrRPUcastRtTLastAction indicates
         an impact that the last message from RTM module had on the value of
         the object tFltrRPDstOperState."
    ::= { tFilterRPlcyUnicastRtTestEntry 4 }

tFilterSystemFilterTableLastChg OBJECT-TYPE
    SYNTAX      TimeStamp
    MAX-ACCESS  read-only
    STATUS      current
    DESCRIPTION
        "The value of the object tFilterSystemFilterTableLastChg
         indicates the sysUpTime at the time of the last modification
         of tFilterSystemFilterTable.

         If no changes were made to the table since the last
         re-initialization of the local network management subsystem,
         then this object contains a zero value."
    ::= { tFilterObjects 68 }

tFilterSystemFilterTable OBJECT-TYPE
    SYNTAX      SEQUENCE OF TFilterSystemFilterEntry
    MAX-ACCESS  not-accessible
    STATUS      current
    DESCRIPTION
        "The table tFilterSystemFilterTable contains information pertaining
         to active IP and IPv6 system filter policies."
    ::= { tFilterObjects 69 }

tFilterSystemFilterEntry OBJECT-TYPE
    SYNTAX      TFilterSystemFilterEntry
    MAX-ACCESS  not-accessible
    STATUS      current
    DESCRIPTION
        "An entry contains details about an active system filter policy.

         Only one active system filter policy per filter type can be configured
         in release 14.0.

         Upon creation of the entry the system filter policy identified by
         the values of the objects tFilterSystemFilterType and
         tFilterSystemFilterId is activated and downloaded to all line cards.

         Regular IP or IPv6 filter policies that have the value of the object
         tIPFilterChainToSystemFilter or tIPv6FilterChainToSystemFilter
         set to 'true(1)' are then chained to the active system filter
         policy. The system filter policy's rules are executed first before
         any rules of the regular filter policy are executed.

         An entry in the table tFilterSystemFilterTable is created and
         destroyed by SNMP SET operations on the object
         tFilterSystemFilterRowStatus.
         
         Furthermore an entry in the table tFilterSystemFilterTable is
         destroyed by the system if an entry with the same value of the object
         tFilterSystemFilterType is created so that there is always at most
         one entry for a given value of tFilterSystemFilterType."
    INDEX { tFilterSystemFilterType, tFilterSystemFilterId }
    ::= { tFilterSystemFilterTable 1 }

TFilterSystemFilterEntry ::= SEQUENCE
    {
        tFilterSystemFilterType         TFilterType,
        tFilterSystemFilterId           TConfigOrVsdFilterID,
        tFilterSystemFilterLastChanged  TimeStamp,
        tFilterSystemFilterRowStatus    RowStatus
    }

tFilterSystemFilterType OBJECT-TYPE
    SYNTAX      TFilterType
    MAX-ACCESS  not-accessible
    STATUS      current
    DESCRIPTION
        "The value of the object tFilterSystemFilterType specifies the filter
         type of the system filter policy to be selected as the active system
         filter policy.

         Only values 'fltrtypeselIp(1)' and 'fltrtypeselIpv6(4)' are supported."
    ::= { tFilterSystemFilterEntry 1 }

tFilterSystemFilterId OBJECT-TYPE
    SYNTAX      TConfigOrVsdFilterID
    MAX-ACCESS  not-accessible
    STATUS      current
    DESCRIPTION
        "The value of the object tFilterSystemFilterId specifies the ID
         of the filter policy to be selected as the active system
         filter policy.

         Values outside of range 1..65535 are reserved for entries dynamically
         created by the system and cannot be used in any SNMP SET operation.

         If the value of the object tFilterSystemFilterType is
         'fltrtypeselIp(1)' then the filter policy with the specified ID must
         exist in tIPFilterTable and must have scope 'system(4)' configured as
         the value of the object tIPFilterScope.

         If the value of the object tFilterSystemFilterType is
         'fltrtypeselIpv6(4)' then the filter policy with the specified ID must
         exist in tIPv6FilterTable and must have scope 'system(4)' configured as
         the value of the object tIPv6FilterScope."
    ::= { tFilterSystemFilterEntry 2 }

tFilterSystemFilterLastChanged OBJECT-TYPE
    SYNTAX      TimeStamp
    MAX-ACCESS  read-only
    STATUS      current
    DESCRIPTION
        "The value of the object tFilterSystemFilterLastChanged indicates
         the timestamp of the last change of this row
         in tFilterSystemFilterTable."
    ::= { tFilterSystemFilterEntry 3 }

tFilterSystemFilterRowStatus OBJECT-TYPE
    SYNTAX      RowStatus
    MAX-ACCESS  read-create
    STATUS      current
    DESCRIPTION
        "The value of the object tFilterSystemFilterRowStatus specifies
         the status of the conceptual row in tFilterSystemFilterTable.

         Rows are created and destroyed by SNMP SET operations on this
         object.

         Only values 'active(1)', 'createAndGo(4)' and 'destroy(6)'
         are supported.
         
         If a row for the same filter type specified by the value of the object
         tFilterSystemFilterType already exists in the table and a new row
         with a different value of the object tFilterSystemFilterId is being
         created the original row is removed by the system."
    ::= { tFilterSystemFilterEntry 4 }

--
-- DHCP6 filter table
--
tDhcp6FilterTblLastChanged OBJECT-TYPE
    SYNTAX      TimeStamp
    MAX-ACCESS  read-only
    STATUS      current
    DESCRIPTION
        "The value of tDhcp6FilterTblLastChanged indicates the sysUpTime
         at the time of the last modification to tDhcp6FilterTable by
         adding, deleting an entry or change to a writable object in the table.

         If no changes were made to the table since the last re-initialization
         of the local network management subsystem, then this object contains a
         zero value."
    ::= { tFilterObjects 70 }

tDhcp6FilterTable OBJECT-TYPE
    SYNTAX      SEQUENCE OF TDhcp6FilterEntry
    MAX-ACCESS  not-accessible
    STATUS      current
    DESCRIPTION
        "Contains a list of all DHCP6 filters configured on this system."
    ::= { tFilterObjects 71 }

tDhcp6FilterEntry OBJECT-TYPE
    SYNTAX      TDhcp6FilterEntry
    MAX-ACCESS  not-accessible
    STATUS      current
    DESCRIPTION
        "Information about a particular DHCP6 filter. Entries are created/deleted
         by user. Entries have a presumed StorageType of nonVolatile."
    INDEX { tDhcp6FilterId }
    ::= { tDhcp6FilterTable 1 }

TDhcp6FilterEntry ::= SEQUENCE
    {
        tDhcp6FilterId                   TDHCPFilterID,
        tDhcp6FilterRowStatus            RowStatus,
        tDhcp6FilterLastChanged          TimeStamp,
        tDhcp6FilterDescription          TItemDescription,
        tDhcp6FilterDefAction            TDhcpFilterAction,
        tDhcp6FilterDefActionFlags       BITS
    }

tDhcp6FilterId OBJECT-TYPE
    SYNTAX      TDHCPFilterID (1..65535)
    MAX-ACCESS  not-accessible
    STATUS      current
    DESCRIPTION
        "Uniquely identifies a DHCP6 filter as configures on this system."
    ::= { tDhcp6FilterEntry 1 }

tDhcp6FilterRowStatus OBJECT-TYPE
    SYNTAX      RowStatus
    MAX-ACCESS  read-create
    STATUS      current
    DESCRIPTION
        "This object allows entries to be created and deleted in the
         tDhcp6FilterTable."
    ::= { tDhcp6FilterEntry 2 }

tDhcp6FilterLastChanged OBJECT-TYPE
    SYNTAX      TimeStamp
    MAX-ACCESS  read-only
    STATUS      current
    DESCRIPTION
        "Indicates the timestamp of the last change to this row."
    ::= { tDhcp6FilterEntry 3 }

tDhcp6FilterDescription OBJECT-TYPE
    SYNTAX      TItemDescription
    MAX-ACCESS  read-create
    STATUS      current
    DESCRIPTION
        "User-provided description for this filter."
    DEFVAL { ''H }
    ::= { tDhcp6FilterEntry 4 }

tDhcp6FilterDefAction OBJECT-TYPE
    SYNTAX      TDhcpFilterAction 
    MAX-ACCESS  read-create
    STATUS      current
    DESCRIPTION
        "The default action to take for DHCP6 host creation requests that do
         not match any of this filter's entries.
         
         The value none(1) specifies normal host creation behaviour, the value
         bypass-host-creation(2) specifies to bypass host creation, the value
         drop(3) specifies to drop the DHCP6 message."
    DEFVAL { none }
    ::= { tDhcp6FilterEntry 5 }

tDhcp6FilterDefActionFlags  OBJECT-TYPE
    SYNTAX      BITS {
                    na  (0),
                    pd  (1)
                }
    MAX-ACCESS  read-create
    STATUS      current
    DESCRIPTION
        "The value of the object tDhcp6FilterDefActionFlags specifies for which
         types of DHCPv6 IAs the bypass-host-creation action is applied."
    REFERENCE
        "RFC 3315"
    ::= { tDhcp6FilterEntry 6 }

--
-- DHCP6 Filter Entry parameters
--
tDhcp6FilterParamsTblLastChanged OBJECT-TYPE
    SYNTAX      TimeStamp
    MAX-ACCESS  read-only
    STATUS      current
    DESCRIPTION
        "The value of tDhcp6FilterParamsTblLastChanged indicates the sysUpTime
         at the time of the last modification to tDhcp6FilterParamsTable by
         adding, deleting an entry or change to a writable object in the table.

         If no changes were made to the table since the last re-initialization
         of the local network management subsystem, then this object contains a
         zero value."
    ::= { tFilterObjects 72 }

tDhcp6FilterParamsTable OBJECT-TYPE
    SYNTAX      SEQUENCE OF TDhcp6FilterParamsEntry
    MAX-ACCESS  not-accessible
    STATUS      current
    DESCRIPTION  "A table of all DHCP6 filter match entries for all DHCP6 filters"
    ::= { tFilterObjects 73 }

tDhcp6FilterParamsEntry OBJECT-TYPE
    SYNTAX      TDhcp6FilterParamsEntry
    MAX-ACCESS  not-accessible
    STATUS      current
    DESCRIPTION
        "Information about a particular DHCP6 filter entry.
        Every DHCP6 filter can have zero or more DHCP6 filter match entries.

        A filter entry with no match criteria set will match every
        packet, and the entry action will be taken.

        Entries are created/deleted by user.

        There is no StorageType object, entries have a presumed
        StorageType of nonVolatile."
    INDEX { tDhcp6FilterId, tDhcp6FilterParamsId }
    ::= { tDhcp6FilterParamsTable 1 }

TDhcp6FilterParamsEntry ::= SEQUENCE
    {
        tDhcp6FilterParamsId             TEntryId,
        tDhcp6FilterParamsRowStatus      RowStatus,
        tDhcp6FilterParamsLastChanged    TimeStamp,
        tDhcp6FilterParamsOptionNumber   INTEGER,
        tDhcp6FilterParamsOptionMatch    TDhcpFilterMatch,
        tDhcp6FilterParamsAction         TDhcpFilterAction,
        tDhcp6FilterParamsOptionValue    OCTET STRING,
        tDhcp6FilterParamsActionFlags    BITS
    }

tDhcp6FilterParamsId OBJECT-TYPE
    SYNTAX      TEntryId
    MAX-ACCESS  not-accessible
    STATUS      current
    DESCRIPTION
        "This is the secondary index for the entry. Every DHCP6 filter can have
         multiple entries, therefore every DHCP6 filter entry is identified by
         the tDhcp6FilterId and tDhcp6FilterParamsId."
    ::= { tDhcp6FilterParamsEntry 1 }

tDhcp6FilterParamsRowStatus OBJECT-TYPE
    SYNTAX      RowStatus
    MAX-ACCESS  read-create
    STATUS      current
    DESCRIPTION
        "This object allows entries to be created and deleted in the
         tDhcp6FilterParamsTable."
    ::= { tDhcp6FilterParamsEntry 2 }

tDhcp6FilterParamsLastChanged OBJECT-TYPE
    SYNTAX      TimeStamp
    MAX-ACCESS  read-only
    STATUS      current
    DESCRIPTION
        "Indicates the timestamp of the last change to this row."
    ::= { tDhcp6FilterParamsEntry 3 }

tDhcp6FilterParamsOptionNumber OBJECT-TYPE
    SYNTAX      INTEGER (-1|0..255)
    MAX-ACCESS  read-create
    STATUS      current
    DESCRIPTION
        "The value of tDhcp6FilterParamsOptionNumber specifies the number of
         the DHCP6 option to filter on."
    REFERENCE
        "RFC 2132, RFC 3315, RFC 3633"
    DEFVAL { -1 }
    ::= { tDhcp6FilterParamsEntry 4 }

tDhcp6FilterParamsOptionMatch OBJECT-TYPE
    SYNTAX      TDhcpFilterMatch
    MAX-ACCESS  read-create
    STATUS      current
    DESCRIPTION
        "The value of tDhcp6FilterParamsOptionMatch specifies the criteria that
         the DHCP6 option must match to trigger this filter entry.

         The value present(1) specifies that the DHCP6 option must be present,
         the value absent(2) specifies that the DHCP6 option must be absent. In
         these cases tDhcp6FilterParamsOptionValue will be reset to an empty
         string.

         A value string(3), string-exact(4), string-invert(5),
         string-exact-invert(6), hex(7), hex-exact(8), hex-invert(9) or
         hex-exact-invert(10) requires an octet string to be present in
         tDhcp6FilterParamsOptionValue to match against.
         "
    DEFVAL { present }
    ::= { tDhcp6FilterParamsEntry 5 }

tDhcp6FilterParamsAction OBJECT-TYPE
    SYNTAX      TDhcpFilterAction
    MAX-ACCESS  read-create
    STATUS      current
    DESCRIPTION
        "The action to take for DHCP6 host creation requests that match this
         filter entry.
         
         The value none(1) specifies normal host creation behaviour, the value
         bypass-host-creation(2) specifies to bypass host creation, the value
         drop(3) specifies to drop the DHCP6 message."
    DEFVAL { none }
    ::= { tDhcp6FilterParamsEntry 6 }

tDhcp6FilterParamsOptionValue OBJECT-TYPE
    SYNTAX      OCTET STRING (SIZE (0..127))
    MAX-ACCESS  read-create
    STATUS      current
    DESCRIPTION
        "The value of the object tDhcp6FilterParamsOptionValue specifies
         the matching pattern for the filtered DHCP6 option.

         This object is mandatory at creation time. A zero length value is only
         allowed when the value of tDhcp6FilterParamsOptionMatch is present(1)
         or absent(2)."
    ::= { tDhcp6FilterParamsEntry 7 }

tDhcp6FilterParamsActionFlags  OBJECT-TYPE
    SYNTAX      BITS {
                    na  (0),
                    pd  (1)
                }
    MAX-ACCESS  read-create
    STATUS      current
    DESCRIPTION
        "The value of the object tDhcp6FilterParamsActionFlags specifies for
         which types of DHCPv6 IAs the bypass-host-creation action is applied."
    REFERENCE
        "RFC 3315"
    ::= { tDhcp6FilterParamsEntry 8 }

-- ----------------------------
--  tFilterEmbedFlowspecTable
-- ----------------------------
tFilterEmbedFlowspecTableLstChg OBJECT-TYPE
    SYNTAX      TimeStamp
    MAX-ACCESS  read-only
    STATUS      current
    DESCRIPTION
        "The value of the object tFilterEmbedFlowspecTableLstChg indicates the
         sysUpTime at the time of the last modification
         of tFilterEmbedFlowspecTable.

         If no changes were made to the table since the last
         re-initialization of the local network management subsystem,
         this object contains the value zero."
    ::= { tFilterObjects 74 }

tFilterEmbedFlowspecTable OBJECT-TYPE
    SYNTAX      SEQUENCE OF TFilterEmbedFlowspecEntry
    MAX-ACCESS  not-accessible
    STATUS      current
    DESCRIPTION
        "The table tFilterEmbedFlowspecTable contains an entry for each
         set of flowspec rules embedded in an IP or IPv6 filter with
         scope other than 'embedded'."
    ::= { tFilterObjects 75 }

tFilterEmbedFlowspecEntry OBJECT-TYPE
    SYNTAX      TFilterEmbedFlowspecEntry
    MAX-ACCESS  not-accessible
    STATUS      current
    DESCRIPTION
        "An entry in the table tFilterEmbedFlowspecTable.

         Entries in this table can be created and deleted via SNMP SET
         operations to tFilterEmbedFlowspecRowStatus.

         Moreover entries are automatically created and deleted by the system
         when a set of flowspec rules is embedded into a filter managed by
         a VSD controller."
    INDEX {tFilterEmbedFlowspecFilterType,
           tFilterEmbedFlowspecInsertFltrId,
           tFilterEmbedFlowspecOffset}
    ::= { tFilterEmbedFlowspecTable 1 }

TFilterEmbedFlowspecEntry ::=
    SEQUENCE {
        tFilterEmbedFlowspecFilterType   TFilterType,
        tFilterEmbedFlowspecInsertFltrId TConfigOrVsdFilterID,
        tFilterEmbedFlowspecOffset       TFilterEmbedOffset,
        tFilterEmbedFlowspecRowStatus    RowStatus,
        tFilterEmbedFlowspecLastChanged  TimeStamp,
        tFilterEmbedFlowspecRtrId        TmnxVRtrID,
        tFilterEmbedFlowspecAdminState   TmnxEmbeddedFltrAdminState,
        tFilterEmbedFlowspecOperState    TmnxEmbeddedFltrOperState
    }

tFilterEmbedFlowspecFilterType OBJECT-TYPE
    SYNTAX      TFilterType
    MAX-ACCESS  not-accessible
    STATUS      current
    DESCRIPTION
        "The value of the object tFilterEmbedFlowspecFilterType specifies the
         type of filter, either IPv4 or IPv6, for the filter specified by
         tFilterEmbedFlowspecInsertFltrId."
    ::= { tFilterEmbedFlowspecEntry 1 }

tFilterEmbedFlowspecInsertFltrId OBJECT-TYPE
    SYNTAX      TConfigOrVsdFilterID
    MAX-ACCESS  not-accessible
    STATUS      current
    DESCRIPTION
        "The value of the object tFilterEmbedFlowspecInsertFltrId specifies the
         filter where the set of flowspec rules configured for the virtual
         router specified by tFilterEmbedFlowspecRtrId is to be embedded.

         Values outside of range 1..65535 are reserved for entries dynamically
         created by the system and cannot be used in any SNMP SET operation."
    ::= { tFilterEmbedFlowspecEntry 2 }

tFilterEmbedFlowspecOffset OBJECT-TYPE
    SYNTAX      TFilterEmbedOffset
    MAX-ACCESS  not-accessible
    STATUS      current
    DESCRIPTION
        "The value of the object tFilterEmbedFlowspecOffset specifies the
         offset of inserted flowspec entries."
    ::= { tFilterEmbedFlowspecEntry 3 }

tFilterEmbedFlowspecRowStatus OBJECT-TYPE
    SYNTAX      RowStatus
    MAX-ACCESS  read-create
    STATUS      current
    DESCRIPTION
        "The value of the object tFilterEmbedFlowspecRowStatus specifies the
         status of a row in tFilterEmbedFlowspecTable. Rows are created and
         destroyed by SNMP SET operations on this object.

         Only values 'active (1)', 'createAndGo(4)', and 'destroy (6)' are
         supported."
    ::= { tFilterEmbedFlowspecEntry 4 }

tFilterEmbedFlowspecLastChanged OBJECT-TYPE
    SYNTAX      TimeStamp
    MAX-ACCESS  read-only
    STATUS      current
    DESCRIPTION
        "The value of tFilterEmbedFlowspecLastChanged indicates the sysUpTime
         at the time of last change to this row in tFilterEmbedFlowspecEntry."
    ::= { tFilterEmbedFlowspecEntry 5 }

tFilterEmbedFlowspecRtrId  OBJECT-TYPE
    SYNTAX      TmnxVRtrID
    MAX-ACCESS  read-create
    STATUS      current
    DESCRIPTION
        "The value of the object tFilterEmbedFlowspecRtrId specifies a virtual
         router for which a set of flowspec rules have been configured by an
         external system. Such flowspec rules will be embedded into the
         embedding filter specified by tFilterEmbedFlowspecFilterType and
         tFilterEmbedFlowspecInsertFltrId.

         At the time of creation of a row via SNMP you can either specify
         or not specify a value for tFilterEmbedFlowspecRtrId.

         If you do not specify the value of tFilterEmbedFlowspecRtrId then
         the system will try to obtain it. This corresponds to the situation
         when the embedding filter has already been assigned to any endpoint.

         If you do not specify the value of tFilterEmbedFlowspecRtrId and the
         embedding filter has not been assigned to any endpoint yet then the
         creation of the row will fail.

         If you specify the value of tFilterEmbedFlowspecRtrId then the system
         will check if the embedding filter has already been assigned to any
         endpoint. If this is not the case it will not be possible to assign
         the embedding filter outside the scope of the virtual router specified
         by tFilterEmbedFlowspecRtrId. If this is the case then the creation of
         the row may be successful only if the value of the virtual router
         specified by tFilterEmbedFlowspecRtrId matches with the value already
         stored in the system.

         In any case the value of tFilterEmbedFlowspecRtrId cannot be changed
         after creation of the row."
    ::= { tFilterEmbedFlowspecEntry 6 }

tFilterEmbedFlowspecAdminState OBJECT-TYPE
    SYNTAX      TmnxEmbeddedFltrAdminState
    MAX-ACCESS  read-create
    STATUS      current
    DESCRIPTION
        "The value of the object tFilterEmbedFlowspecAdminState specifies the
         administrative state of the embed request defined by this row.

         If an active embedding cannot be fulfilled due to dynamic events,
         this object will be set to 'inactive' automatically by the system.
         In those cases, the value of the object tFilterEmbedFlowspecOperState
         will indicate the failure reason."
    DEFVAL { active }
    ::= { tFilterEmbedFlowspecEntry 7 }

tFilterEmbedFlowspecOperState OBJECT-TYPE
    SYNTAX      TmnxEmbeddedFltrOperState
    MAX-ACCESS  read-only
    STATUS      current
    DESCRIPTION
        "The value of tFilterEmbedFlowspecOperState indicates the operational
         state of the embed request defined by this row."
    ::= { tFilterEmbedFlowspecEntry 8 }

-- ----------------------------
--  tFltrEmbFlowspecInfoTable
-- ----------------------------

tFltrEmbFlowspecInfoTable OBJECT-TYPE
    SYNTAX      SEQUENCE OF TFltrEmbFlowspecInfoEntry
    MAX-ACCESS  not-accessible
    STATUS      current
    DESCRIPTION
        "The table tFltrEmbFlowspecInfoTable contains an entry for each
         auto-created embedded filter for flowspec rules inserted in an
         IP or IPv6 filter with scope other than 'embedded'.

         This row complements the corresponding row in the
         tFilterEmbedFlowspecTable with read-only operational info."
    ::= { tFilterObjects 76 }

tFltrEmbFlowspecInfoEntry OBJECT-TYPE
    SYNTAX      TFltrEmbFlowspecInfoEntry
    MAX-ACCESS  not-accessible
    STATUS      current
    DESCRIPTION
        "An entry in the tFltrEmbFlowspecInfoTable."
    AUGMENTS {tFilterEmbedFlowspecEntry}
    ::= { tFltrEmbFlowspecInfoTable 1 }

TFltrEmbFlowspecInfoEntry ::=
    SEQUENCE {
        tFltrEmbFlowSpecInfoFltrId           TAnyFilterID,
        tFltrEmbFlowSpecInfoEntryCnt         Unsigned32,
        tFltrEmbFlowSpecInfoEntryCntIns      Unsigned32
    }

tFltrEmbFlowSpecInfoFltrId OBJECT-TYPE
    SYNTAX      TAnyFilterID
    MAX-ACCESS  read-only
    STATUS      current
    DESCRIPTION
        "The value of the object tFltrEmbFlowSpecInfoFltrId indicates the ID
         of the auto-created embedded filter for flowspec rules related to the
         virtual router specified by tFilterEmbedFlowspecRtrId."
    ::= { tFltrEmbFlowspecInfoEntry 1 }

tFltrEmbFlowSpecInfoEntryCnt OBJECT-TYPE
    SYNTAX      Unsigned32
    MAX-ACCESS  read-only
    STATUS      current
    DESCRIPTION
        "The value of the object tFltrEmbFlowSpecInfoEntryCnt indicates
         how many entries are present in the embedded filter specified by
         tFltrEmbFlowSpecInfoFltrId."
    ::= { tFltrEmbFlowspecInfoEntry 2 }

tFltrEmbFlowSpecInfoEntryCntIns OBJECT-TYPE
    SYNTAX      Unsigned32
    MAX-ACCESS  read-only
    STATUS      current
    DESCRIPTION
        "The value of the object tFltrEmbFlowSpecInfoEntryCntIns
         indicates how many entries of the embedded filter (specified by
         tFltrEmbFlowSpecInfoFltrId) are actually inserted into the
         embedding filter (specified by tFilterEmbedFlowspecInsertFltrId).

         If the object tFilterEmbedFlowspecOperState is different from 'active'
         this object will always be zero.

         Otherwise the difference between tFltrEmbFlowSpecInfoEntryCnt and
         the value of this object indicates how many entries of the embedded
         filter were overwritten by local entries in the embedding filter."
    ::= { tFltrEmbFlowspecInfoEntry 3 }

-- --------------------------------
--  tFltrEmbFlowspecEntryInfoTable
-- --------------------------------

tFltrEmbFlowspecEntryInfoTable OBJECT-TYPE
    SYNTAX      SEQUENCE OF TFltrEmbFlowspecEntryInfoEntry
    MAX-ACCESS  not-accessible
    STATUS      current
    DESCRIPTION
        "The table tFltrEmbFlowspecEntryInfoTable contains an entry for each
         entry of an auto-created embedded filter for flowspec rules inserted
         in an IP or IPv6 filter with scope other than 'embedded'"
    ::= { tFilterObjects 77 }

tFltrEmbFlowspecEntryInfoEntry OBJECT-TYPE
    SYNTAX      TFltrEmbFlowspecEntryInfoEntry
    MAX-ACCESS  not-accessible
    STATUS      current
    DESCRIPTION
        "An entry in the tFltrEmbFlowspecEntryInfoTable.
         Rows in the tFltrEmbFlowspecEntryInfoTable are created
         by the SYSTEM when an auto-created embedded filter for flowspec rules
         is inserted into an IP or IPv6 filter with scope other than
         'embedded'. They are destroyed by the SYSTEM when such auto-created
         embedded filter is removed from an IP or IPv6 filter with scope other
         than 'embedded'."
    INDEX {tFilterEmbedFlowspecFilterType,
           tFilterEmbedFlowspecInsertFltrId,
           tFltrEmbFlowspecEntryId}
    ::= { tFltrEmbFlowspecEntryInfoTable 1 }

TFltrEmbFlowspecEntryInfoEntry ::=
    SEQUENCE {
        tFltrEmbFlowspecEntryId           TEntryId,
        tFltrEmbFlowspecEntryInsEntryId   TEmbedInsrtEntryId,
        tFltrEmbFlowspecEntryOperState    TmnxFltrEmbeddedEntryState
    }

tFltrEmbFlowspecEntryId OBJECT-TYPE
    SYNTAX      TEntryId
    MAX-ACCESS  not-accessible
    STATUS      current
    DESCRIPTION
        "The value of the object tFltrEmbFlowspecEntryId specifies the ID of
         the entry inside of the auto-created embedded filter for flowspec
         rules specified by tFltrEmbFlowSpecInfoFltrId."
    ::= { tFltrEmbFlowspecEntryInfoEntry 1 }

tFltrEmbFlowspecEntryInsEntryId OBJECT-TYPE
    SYNTAX      TEmbedInsrtEntryId
    MAX-ACCESS  read-only
    STATUS      current
    DESCRIPTION
        "The value of the object tFltrEmbFlowspecEntryInsEntryId indicates
         which entry in the IP or IPv6 filter with scope other than 'embedded'
         specified by tFilterEmbedFlowspecInsertFltrId corresponds to the entry
         specified by tFltrEmbFlowspecEntryId in the auto-created embedded
         filter for flowspec rules specified by tFltrEmbFlowSpecInfoFltrId."
    ::= { tFltrEmbFlowspecEntryInfoEntry 2 }

tFltrEmbFlowspecEntryOperState OBJECT-TYPE
    SYNTAX      TmnxFltrEmbeddedEntryState
    MAX-ACCESS  read-only
    STATUS      current
    DESCRIPTION
        "The value of the object tFltrEmbFlowspecEntryOperState indicates
         the current operational state of the entry identified
         by tFltrEmbFlowspecEntryId of the embedded filter identified
         by tFltrEmbFlowSpecInfoFltrId that is embedded into the filter
         identified by tFilterEmbedFlowspecInsertFltrId."
    ::= { tFltrEmbFlowspecEntryInfoEntry 3 }

-- ----------------------------
--  tFilterEmbedVsdTable
-- ----------------------------

tFilterEmbedVsdTableLstChg OBJECT-TYPE
    SYNTAX      TimeStamp
    MAX-ACCESS  read-only
    STATUS      current
    DESCRIPTION
        "The value of the object tFilterEmbedVsdTableLstChg indicates
         the sysUpTime at the time of the last modification
         of tFilterEmbedVsdTable.

         If no changes were made to the table since the last
         re-initialization of the local network management subsystem,
         this object contains the value zero."
    ::= { tFilterObjects 78 }

tFilterEmbedVsdTable OBJECT-TYPE
    SYNTAX      SEQUENCE OF TFilterEmbedVsdEntry
    MAX-ACCESS  not-accessible
    STATUS      current
    DESCRIPTION
        "The table tFilterEmbedVsdTable contains an entry for each
         filter managed by a VSD controller embedded in a filter with
         scope other than 'embedded'.

         A dedicated embedded filter under the management of the VSD controller
         contains all required dynamic steering rules.
         This set of rules is inserted into a filter (that has scope
         other than 'embedded') created by an administrator containing static
         (security) rules that is applied on interfaces.

         This way the administrator has full control of the position (offset)
         at which the rules are inserted in order not to compromise security
         while the VSD controller can dynamically alter the steering rules
         as necessary."
    ::= { tFilterObjects 79 }

tFilterEmbedVsdEntry OBJECT-TYPE
    SYNTAX      TFilterEmbedVsdEntry
    MAX-ACCESS  not-accessible
    STATUS      current
    DESCRIPTION
        "An entry in the table tFilterEmbedVsdTable.

         Entries in this table can be created and deleted via SNMP SET
         operations to tFilterEmbedVsdRowStatus.

         Moreover entries are automatically created and deleted by the system
         when one filter managed by a VSD controller
         is embedded into another filter managed by a VSD controller."
    INDEX {tFilterEmbedVsdFilterType,
           tFilterEmbedVsdInsertFltrId,
           tFilterEmbedVsdEmbeddedFltrId,
           tFilterEmbedVsdOffset}
    ::= { tFilterEmbedVsdTable 1 }

TFilterEmbedVsdEntry ::=
    SEQUENCE {
        tFilterEmbedVsdFilterType     TFilterType,
        tFilterEmbedVsdInsertFltrId   TConfigOrVsdFilterID,
        tFilterEmbedVsdEmbeddedFltrId TVsdFilterID,
        tFilterEmbedVsdOffset         TFilterEmbedOffset,
        tFilterEmbedVsdRowStatus      RowStatus,
        tFilterEmbedVsdLastChanged    TimeStamp,
        tFilterEmbedVsdAdminState     TmnxEmbeddedFltrAdminState,
        tFilterEmbedVsdOperState      TmnxEmbeddedFltrOperState
    }

tFilterEmbedVsdFilterType OBJECT-TYPE
    SYNTAX      TFilterType
    MAX-ACCESS  not-accessible
    STATUS      current
    DESCRIPTION
        "The value of the object tFilterEmbedVsdFilterType specifies
         the type of filter for the filters specified by
         tFilterEmbedVsdEmbeddedFltrId and tFilterEmbedVsdInsertFltrId.
         In release 14.0 only values 'fltrtypeselIp (1)',
         'fltrtypeselMac (2)' and 'fltrtypeselIpv6 (4)' are supported.
          "
    ::= { tFilterEmbedVsdEntry 1 }

tFilterEmbedVsdInsertFltrId OBJECT-TYPE
    SYNTAX      TConfigOrVsdFilterID
    MAX-ACCESS  not-accessible
    STATUS      current
    DESCRIPTION
        "The value of the object tFilterEmbedVsdInsertFltrId specifies
         the ID of the filter with scope other than 'embedded' where
         the filter managed by a VSD controller specified
         by tFilterEmbedVsdEmbeddedFltrId is to be inserted.

         Values outside of range 1..65535 are reserved for entries dynamically
         created by the system and cannot be used in any SNMP SET operation."
    ::= { tFilterEmbedVsdEntry 2 }

tFilterEmbedVsdEmbeddedFltrId OBJECT-TYPE
    SYNTAX      TVsdFilterID
    MAX-ACCESS  not-accessible
    STATUS      current
    DESCRIPTION
        "The value of the object tFilterEmbedVsdEmbeddedFltrId specifies
         the ID of the filter managed by a VSD controller to be inserted
         in the filter with scope other than 'embedded' specified
         by tFilterEmbedVsdInsertFltrId."
    ::= { tFilterEmbedVsdEntry 3 }

tFilterEmbedVsdOffset OBJECT-TYPE
    SYNTAX      TFilterEmbedOffset
    MAX-ACCESS  not-accessible
    STATUS      current
    DESCRIPTION
        "The value of the object tFilterEmbedVsdOffset specifies the offset
         of inserted entries."
    ::= { tFilterEmbedVsdEntry 4 }

tFilterEmbedVsdRowStatus OBJECT-TYPE
    SYNTAX      RowStatus
    MAX-ACCESS  read-create
    STATUS      current
    DESCRIPTION
        "The value of the object tFilterEmbedVsdRowStatus specifies
         the status of a row in tFilterEmbedVsdTable. Rows are created
         and destroyed by SNMP SET operations on this object.

         Only values 'active (1)', 'createAndGo(4)', and 'destroy (6)' are
         supported."
    ::= { tFilterEmbedVsdEntry 5 }

tFilterEmbedVsdLastChanged OBJECT-TYPE
    SYNTAX      TimeStamp
    MAX-ACCESS  read-only
    STATUS      current
    DESCRIPTION
        "The value of tFilterEmbedVsdLastChanged indicates the sysUpTime
         at the time of last change to this row in tFilterEmbedVsdTable."
    ::= { tFilterEmbedVsdEntry 6 }

tFilterEmbedVsdAdminState OBJECT-TYPE
    SYNTAX      TmnxEmbeddedFltrAdminState
    MAX-ACCESS  read-create
    STATUS      current
    DESCRIPTION
        "The value of the object tFilterEmbedVsdAdminState specifies
         the administrative state of the embed request defined by this row.

         If an active embedding cannot be fulfilled due to dynamic events,
         this object will be set to 'inactive' automatically by the system.
         In those cases, the value of the object tFilterEmbedVsdOperState
         will indicate the failure reason."
    DEFVAL { active }
    ::= { tFilterEmbedVsdEntry 7 }

tFilterEmbedVsdOperState OBJECT-TYPE
    SYNTAX      TmnxEmbeddedFltrOperState
    MAX-ACCESS  read-only
    STATUS      current
    DESCRIPTION
        "The value of the object tFilterEmbedVsdOperState indicates
         the operational state of the embed request defined by this row."
    ::= { tFilterEmbedVsdEntry 8 }

-- ----------------------------
--  tFilterEmbedVsdInfoTable
-- ----------------------------

tFilterEmbedVsdInfoTable OBJECT-TYPE
    SYNTAX      SEQUENCE OF TFilterEmbedVsdInfoEntry
    MAX-ACCESS  not-accessible
    STATUS      current
    DESCRIPTION
        "The table tFilterEmbedVsdInfoTable contains an entry
         for each embedded filter managed by a VSD controller inserted
         in a filter with scope other than 'embedded'.

         This row complements the corresponding row in the
         tFilterEmbedVsdTable with read-only operational info."
    ::= { tFilterObjects 80 }

tFilterEmbedVsdInfoEntry OBJECT-TYPE
    SYNTAX      TFilterEmbedVsdInfoEntry
    MAX-ACCESS  not-accessible
    STATUS      current
    DESCRIPTION
        "An entry in the tFilterEmbedVsdInfoTable."
    AUGMENTS {tFilterEmbedVsdEntry}
    ::= { tFilterEmbedVsdInfoTable 1 }

TFilterEmbedVsdInfoEntry ::=
    SEQUENCE {
        tFltrEmbedVsdInfoEntryCnt         Unsigned32,
        tFltrEmbedVsdInfoEntryCntInsrtd   Unsigned32
    }

tFltrEmbedVsdInfoEntryCnt OBJECT-TYPE
    SYNTAX      Unsigned32
    MAX-ACCESS  read-only
    STATUS      current
    DESCRIPTION
        "The value of the object tFltrEmbedVsdInfoEntryCnt indicates how many
         entries are present in the embedded filter managed by a VSD controller
         (specified by tFilterEmbedVsdEmbeddedFltrId)."
    ::= { tFilterEmbedVsdInfoEntry 1 }

tFltrEmbedVsdInfoEntryCntInsrtd OBJECT-TYPE
    SYNTAX      Unsigned32
    MAX-ACCESS  read-only
    STATUS      current
    DESCRIPTION
        "The value of the object tFltrEmbedVsdInfoEntryCntInsrtd indicates
         how many entries of the embedded filter managed by a VSD controller
         (specified by tFilterEmbedVsdEmbeddedFltrId) are actually inserted
         into the embedding filter (specified by tFilterEmbedVsdInsertFltrId).

         If the object tFilterEmbedVsdOperState is different from 'active'
         this object will always be zero.

         Otherwise the difference between the value of this object
         and the value of tFltrEmbedVsdInfoEntryCnt indicates how many entries
         of the embedded filter were overwritten by local entries
         in the embedding filter."
    ::= { tFilterEmbedVsdInfoEntry 2 }

-- ----------------------------
--  tFilterEmbedVsdEntryInfoTable
-- ----------------------------

tFilterEmbedVsdEntryInfoTable OBJECT-TYPE
    SYNTAX      SEQUENCE OF TFilterEmbedVsdEntryInfoEntry
    MAX-ACCESS  not-accessible
    STATUS      current
    DESCRIPTION
        "The table tFilterEmbedVsdEntryInfoTable contains an entry
         for each entry of an embedded filter managed by a VSD controller
         inserted in a filter with scope other than 'embedded'"
    ::= { tFilterObjects 81 }

tFilterEmbedVsdEntryInfoEntry OBJECT-TYPE
    SYNTAX      TFilterEmbedVsdEntryInfoEntry
    MAX-ACCESS  not-accessible
    STATUS      current
    DESCRIPTION
        "An entry in the tFilterEmbedVsdEntryInfoTable.
         Rows in the tFilterEmbedVsdEntryInfoTable are created
         by the SYSTEM when an embedded filter managed by a VSD controller
         is inserted into a filter with scope other than 'embedded'.
         They are destroyed by the SYSTEM when an embedded filter managed
         by a VSD controller is removed from a filter with scope other
         than 'embedded'."
    INDEX {tFilterEmbedVsdFilterType,
           tFilterEmbedVsdInsertFltrId,
           tFilterEmbedVsdEmbeddedFltrId,
           tFilterEmbedVsdEntryId}
    ::= { tFilterEmbedVsdEntryInfoTable 1 }

TFilterEmbedVsdEntryInfoEntry ::=
    SEQUENCE {
        tFilterEmbedVsdEntryId           TEntryId,
        tFilterEmbedVsdEntryInsrtEntryId TEmbedInsrtEntryId,
        tFilterEmbedVsdEntryOperState    TmnxFltrEmbeddedEntryState
    }

tFilterEmbedVsdEntryId OBJECT-TYPE
    SYNTAX      TEntryId
    MAX-ACCESS  not-accessible
    STATUS      current
    DESCRIPTION
        "The value of the object tFilterEmbedVsdEntryId specifies
         the ID of the entry inside of the embedded filter managed by a VSD
         controller specified by tFilterEmbedVsdEmbeddedFltrId."
    ::= { tFilterEmbedVsdEntryInfoEntry 1 }

tFilterEmbedVsdEntryInsrtEntryId OBJECT-TYPE
    SYNTAX      TEmbedInsrtEntryId
    MAX-ACCESS  read-only
    STATUS      current
    DESCRIPTION
        "The value of the object tFilterEmbedVsdEntryInsrtEntryId indicates
         which entry in the filter with scope other than 'embedded' specified
         by tFilterEmbedVsdInsertFltrId corresponds to the entry specified
         by tFilterEmbedVsdEntryId in the filter managed by a VSD controller
         specified by tFilterEmbedVsdEmbeddedFltrId."
    ::= { tFilterEmbedVsdEntryInfoEntry 2 }

tFilterEmbedVsdEntryOperState OBJECT-TYPE
    SYNTAX      TmnxFltrEmbeddedEntryState
    MAX-ACCESS  read-only
    STATUS      current
    DESCRIPTION
        "The value of the object tFilterEmbedVsdEntryOperState indicates
         the current operational state of the entry identified
         by tFilterEmbedVsdEntryId of the embedded filter identified
         by tFilterEmbedVsdEmbeddedFltrId that is embedded into the filter
         identified by tFilterEmbedVsdInsertFltrId."
    ::= { tFilterEmbedVsdEntryInfoEntry 3 }

--
--Mac Filter Entry Action table
--

tMacFltrEntryActionTblLChg OBJECT-TYPE
    SYNTAX      TimeStamp
    MAX-ACCESS  read-only
    STATUS      current
    DESCRIPTION
       "The value of the object tMacFltrEntryActionTblLChg indicates the
        sysUpTime at the time of the last modification of
        tMacFltrEntryActionTable.

        If no changes were made to the table since the last re-initialization of
        the local network management subsystem, then this object contains a zero
        value."
    ::= { tFilterObjects 82 }

tMacFltrEntryActionTable OBJECT-TYPE
    SYNTAX      SEQUENCE OF TMacFltrEntryActionEntry
    MAX-ACCESS  not-accessible
    STATUS      current
    DESCRIPTION
        "The table tMacFltrEntryActionTable contains information pertaining to
         redundant MAC filter entry actions. Prior to introduction of
         tMacFltrEntryActionTable MAC filter actions were configured via
         tMacFilterParamsTable. Via tMacFilterParamsTable it is possible to
         configure only one action per filter entry. tMacFltrEntryActionTable is
         introduced to override the functionality of tMacFilterParamsTable
         regarding the action configuration. tMacFltrEntryActionTable supports
         configuration of redundant filter actions. Functionality related to
         actions added after introduction of tMacFltrEntryActionTable is
         supported only via tMacFltrEntryActionTable.

         Filter actions available prior to introduction of
         tMacFltrEntryActionTable can be configured via specifying action
         parameters in tMacFilterParamsTable or via tMacFltrEntryActionTable.
         It's recommended to use tMacFltrEntryActionTable.

         Configuration via tMacFilterParamsTable:
           - only actions available prior to introduction of
             tMacFltrEntryActionTable are allowed:
             When an entry is created in tMacFilterParamsTable then an entry
             with the value of tMacFltrEntryActActionId equal to 'primary' is
             created in tMacFltrEntryActionTable by the system. If an action is
             configured via tMacFilterParamsTable, then this new system created
             entry in tMacFltrEntryActionTable will contain interpretation of
             values pertaining to configured action in tMacFilterParamsEntry.

         Configuration via tMacFltrEntryActionTable:
           - action available prior to introduction of tMacFltrEntryActionTable:
             If an action which was available prior to introduction of
             tMacFltrEntryActionTable is configured via tMacFltrEntryActionTable
             and the value of tMacFltrEntryActActionId for that action is equal
             to 'primary' then the action related objects in the table
             tMacFilterParamsAction will be automatically set by the system to
             the interpretation of the values in tMacFltrEntryActionTable
             pertaining to that action.

           - action not available prior to introduction of
             tMacFltrEntryActionTable: If an action not available prior to
             introduction of tMacFltrEntryActionTable is configured then the
             value of tMacFilterParamsAction is set to 'unrecognized' by the
             system. The value 'unrecognized' indicates that functionality not
             supported by tMacFilterParamsTable was configured and therefore
             action related objects in the tMacFilterParamsTable are not valid
             and shouldn't be used for configuration."
    ::= { tFilterObjects 83 }

tMacFltrEntryActionEntry OBJECT-TYPE
    SYNTAX      TMacFltrEntryActionEntry
    MAX-ACCESS  not-accessible
    STATUS      current
    DESCRIPTION
        "The entry contains information pertaining to an action for
         a particular MAC filter entry (object corresponding to MAC filter entry
         is tMacFilterParamsEntry). Per one filter entry up to two actions
         can be configured (primary and secondary).

         Entries with the value of tMacFltrEntryActActionId equal to 'primary'
         are created and destroyed by SNMP SET operations on the object
         tMacFilterParamsRowStatus. Entries with the value of
         tMacFltrEntryActActionId equal to 'secondary' are created by SNMP SET
         operation on the object tMacFltrEntryActRowStatus and destroyed by SNMP
         SET operation on the objects tMacFltrEntryActRowStatus or
         tMacFilterParamsRowStatus."
    INDEX { tMacFilterId, tMacFilterParamsIndex, tMacFltrEntryActActionId }
    ::= { tMacFltrEntryActionTable 1 }

TMacFltrEntryActionEntry ::= SEQUENCE
    {
        tMacFltrEntryActActionId         TFilterEntryActionId,
        tMacFltrEntryActLastChanged      TimeStamp,
        tMacFltrEntryActRowStatus        RowStatus,
        tMacFltrEntryActAction           TMacFilterEntryAction,
        tMacFltrEntryActFwdSapPortId     TmnxPortID,
        tMacFltrEntryActFwdSapEncapVal   TmnxEncapVal,
        tMacFltrEntryActFwdSdpBind       SdpBindId,
        tMacFltrEntryActRedirectURL      TmnxHttpRedirectUrl,
        tMacFltrEntryActEsi              TFilterEsi,
        tMacFltrEntryActFwdEsiSvcId      TmnxServId,
        tMacFltrEntryActRateLimit        TFilterEntryActionRateLimit,
        tMacFltrEntryActPbrTargetStatus  TFilterPbrTargetStatus
    }

tMacFltrEntryActActionId OBJECT-TYPE
    SYNTAX      TFilterEntryActionId
    MAX-ACCESS  not-accessible
    STATUS      current
    DESCRIPTION
        "The value of the object tMacFltrEntryActActionId specifies a unique
         identifier of an action within the filter entry. Per one filter entry
         up to two actions can be configured (the primary and the secondary).
         PBF destination availability checking for an entry is turned on when
         both actions (the primary and the secondary) are configured for an
         entry. This is allowed only for the following combinations of actions:
            - both actions are PBF to SAP
            - both actions are PBF to SDP
            - the primary action is PBF to SAP and the secondary action is
              PBF to SDP or vice-versa

         If the PBF destination of the primary action is available, then the
         primary action will be taken on a packet matching the filter entry. If
         the PBF destination of the primary action is not available and the PBF
         destination of the secondary action is available then the secondary
         action will be taken on a packet matching the filter entry. If none of
         the actions for the entry has an available PBF destination then the
         action specified by the object tMacFilterParamsPbrDwnActOvr will be
         taken on a packet matching the filter entry.

         There is a limit to the number of filter entries with the destination
         availability checking turned on."
    ::= { tMacFltrEntryActionEntry 1 }

tMacFltrEntryActLastChanged OBJECT-TYPE
    SYNTAX      TimeStamp
    MAX-ACCESS  read-only
    STATUS      current
    DESCRIPTION
        "The value of the object tMacFltrEntryActLastChanged indicates the
         sysUpTime at the time of the last modification of
         tMacFltrEntryActionEntry.

         If no changes were made to the entry since the last re-initialization
         of the local network management subsystem, then this object contains
         a zero value."
    ::= { tMacFltrEntryActionEntry 2 }

tMacFltrEntryActRowStatus OBJECT-TYPE
    SYNTAX      RowStatus
    MAX-ACCESS  read-create
    STATUS      current
    DESCRIPTION
        "The value of the object tMacFltrEntryActRowStatus specifies the status
         of the conceptual row in tMacFltrEntryActionTable.

         Rows with value of tMacFltrEntryActActionId equal to 'primary' are
         created and destroyed by SNMP SET operations on the object
         tMacFilterParamsRowStatus. Rows with value of tMacFltrEntryActActionId
         equal to 'secondary' are created by SNMP SET operation on the object
         tMacFltrEntryActRowStatus and destroyed by SNMP SET operation on the
         objects tMacFltrEntryActRowStatus or tMacFilterParamsRowStatus."
    ::= { tMacFltrEntryActionEntry 3 }

tMacFltrEntryActAction OBJECT-TYPE
    SYNTAX      TMacFilterEntryAction
    MAX-ACCESS  read-create
    STATUS      current
    DESCRIPTION
        "The value of the object tMacFltrEntryActAction specifies the action
         to be taken on a packet matching the filter entry.

         Refer to the description of the textual convention
         TMacFilterEntryAction for more information."
    DEFVAL { drop }
    ::= { tMacFltrEntryActionEntry 4 }

tMacFltrEntryActFwdSapPortId OBJECT-TYPE
    SYNTAX      TmnxPortID
    MAX-ACCESS  read-create
    STATUS      current
    DESCRIPTION
        "The value of the object tMacFltrEntryActFwdSapPortId specifies the sap
         port identity of the destination for this MAC filter entry. A value of
         0 indicates that there is currently no SAP destination specified.
         A value different from 0 can only be specified if the value of
         tMacFltrEntryActAction is 'forwardSap' and the value of
         tMacFltrEntryActFwdSdpBind has a zero value.

         Note that the value of tMacFltrEntryActFwdSapPortId is silently
         cleared by the system if tMacFltrEntryActAction is set to
         value other than 'forwardSap'."
    DEFVAL { 0 }
    ::= { tMacFltrEntryActionEntry 5 }

tMacFltrEntryActFwdSapEncapVal OBJECT-TYPE
    SYNTAX      TmnxEncapVal
    MAX-ACCESS  read-create
    STATUS      current
    DESCRIPTION
        "The value of the object tMacFltrEntryActFwdSapEncapVal specifies the
         sap port encap value of the destination SAP for this MAC filter entry.
         A value different from 0 can only be specified when the
         tMacFltrEntryActFwdSapPortId object has a non zero value, and the
         value of the tMacFltrEntryActAction object of this entry is
         'forwardSap'.
         A value of 0 indicates that either
         1) the sap encapsulation value is not specified when
            tMacFltrEntryActFwdSapPortId and tMacFilterParamsFwdSvcId
            have valid values; or
         2) that there is no SAP destination.

         Note that the value of tMacFltrEntryActFwdSapEncapVal is silently
         cleared by the system if tMacFltrEntryActAction is set to value other
         than 'forwardSap'."
    DEFVAL { 0 }
    ::= { tMacFltrEntryActionEntry 6 }

tMacFltrEntryActFwdSdpBind OBJECT-TYPE
    SYNTAX      SdpBindId
    MAX-ACCESS  read-create
    STATUS      current
    DESCRIPTION
        "The value of the object tMacFltrEntryActFwdSdpBind specifies the sdp
         bind identity of the destination for this MAC filter entry. A value of
         0 indicates that there is currently no SDP binding defined. A value
         different from 0 can only be specified if the value of
         tMacFltrEntryActAction is 'forwardSdp' and
         tMacFltrEntryActFwdSapPortId and tMacFltrEntryActFwdSapEncapVal have
         a zero value.

         Note that the value of tMacFltrEntryActFwdSdpBind is silently cleared
         by the system if tMacFltrEntryActAction is set to value other than
         'forwardSdp'."
    DEFVAL { '0000000000000000'H }
    ::= { tMacFltrEntryActionEntry 7 }

tMacFltrEntryActRedirectURL OBJECT-TYPE
    SYNTAX      TmnxHttpRedirectUrl
    MAX-ACCESS  read-create
    STATUS      current
    DESCRIPTION
        "The value of the object tMacFltrEntryActRedirectURL specifies the URL
         to redirect to, when the value of tMacFltrEntryActAction is
         'httpRedirect'.

         Note that the value of tMacFltrEntryActRedirectURL is silently cleared
         by the system if tMacFltrEntryActAction is set to value other than
         'httpRedirect'."
    DEFVAL { ''H }
    ::= { tMacFltrEntryActionEntry 8 }

tMacFltrEntryActEsi OBJECT-TYPE
    SYNTAX      TFilterEsi
    MAX-ACCESS  read-create
    STATUS      current
    DESCRIPTION
        "The value of the object tMacFltrEntryActEsi specifies the ethernet
         segment identifier (ESI) of the first ESI identified appliance in Nuage
         service chain. When the value of tMacFilterParamsAction is
         'forwardEsiL2' packets matching the filter entry are forwarded to the
         appliance using EVPN-resolved VXLAN tunnel in the specified VPLS
         service (tMacFltrEntryActFwdEsiSvcId).

         The value '0' indicates that there is no ESI specified.

         The non zero value of tMacFltrEntryActEsi must be set together with a
         non zero value of tMacFltrEntryActFwdEsiSvcId and value of
         tMacFltrEntryActAction set to 'forwardEsiL2'.

         Note that the value of tMacFltrEntryActEsi is silently cleared by the
         system if the value of tMacFltrEntryActAction is set to any value other
         than 'forwardEsiL2'."
    DEFVAL { '00000000000000000000'H }
    ::= { tMacFltrEntryActionEntry 9 }

tMacFltrEntryActFwdEsiSvcId OBJECT-TYPE
    SYNTAX      TmnxServId
    MAX-ACCESS  read-create
    STATUS      current
    DESCRIPTION
        "The value of the object tMacFltrEntryActFwdEsiSvcId specifies the
         identifier of the VPLS used for VPN/DC connectivity.

         The value '0' indicates that no VPLS identifier is specified.

         The non zero value of tMacFltrEntryActFwdEsiSvcId must be set together
         with a non zero value of tMacFltrEntryActEsi and value of
         tMacFltrEntryActAction set to 'forwardEsiL2'.

         Note that the value of tMacFltrEntryActFwdEsiSvcId is silently cleared
         by the system if the value of tMacFltrEntryActAction is set to any
         value other than 'forwardEsiL2'."
    DEFVAL { 0 }
    ::= { tMacFltrEntryActionEntry 10 }

tMacFltrEntryActRateLimit OBJECT-TYPE
    SYNTAX      TFilterEntryActionRateLimit
    UNITS       "kbps"
    MAX-ACCESS  read-create
    STATUS      current
    DESCRIPTION
        "The value of the object tMacFltrEntryActRateLimit specifies the
         rate to which the traffic matching the filter entry will be limited.

         The value of tMacFltrEntryActRateLimit can be set to non default value
         only if the value of tMacFltrEntryActAction is set to 'rateLimit'.

         Note that the value of tMacFltrEntryActRateLimit is silently cleared
         by the system if the value of tMacFltrEntryActAction is set to any
         value other than 'rateLimit'."
    DEFVAL { 0 }
    ::= { tMacFltrEntryActionEntry 11 }

tMacFltrEntryActPbrTargetStatus OBJECT-TYPE
    SYNTAX      TFilterPbrTargetStatus
    MAX-ACCESS  read-only
    STATUS      current
    DESCRIPTION
        "The value of the object tMacFltrEntryActPbrTargetStatus indicates the
         PBR target status.

         Refer to the description of the textual convention
         TFilterPbrTargetStatus for more information."
    ::= { tMacFltrEntryActionEntry 12 }

--
--IP/IPv6 Filter Entry Action table
--

tIPvXFltrEntryActionTblLChg OBJECT-TYPE
    SYNTAX      TimeStamp
    MAX-ACCESS  read-only
    STATUS      current
    DESCRIPTION
       "The value of the object tIPvXFltrEntryActionTblLChg indicates the
        sysUpTime at the time of the last modification of
        tIPvXFltrEntryActionTable.

        If no changes were made to the table since the last re-initialization of
        the local network management subsystem, then this object contains a zero
        value."
    ::= { tFilterObjects 84 }

tIPvXFltrEntryActionTable OBJECT-TYPE
    SYNTAX      SEQUENCE OF TIPvXFltrEntryActionEntry
    MAX-ACCESS  not-accessible
    STATUS      current
    DESCRIPTION
        "The table tIPvXFltrEntryActionTable contains information pertaining to
         redundant IPv4 and IPv6 filter entry actions. Prior to introduction of
         tIPvXFltrEntryActionTable IPv4 filter actions were configured via
         tIPFilterParamsTable and tIPFilterParamsExtTable. IPv6 filter actions
         were configured via tIPv6FilterParamsTable and
         tIPv6FilterParamsExtTable. Via these original tables it is possible to
         configure only one action per filter entry. tIPvXFltrEntryActionTable
         is introduced to override the functionality of the original tables
         regarding the action configuration. tIPvXFltrEntryActionTable supports
         configuration of redundant filter actions. Functionality related to
         actions added after introduction of tIPvXFltrEntryActionTable is
         supported only via tIPvXFltrEntryActionTable.

         Filter actions available prior to introduction of
         tIPvXFltrEntryActionTable can be configured via specifying action
         parameters in the original tables or via tIPvXFltrEntryActionTable.
         It's recommended to use tIPvXFltrEntryActionTable.

         Configuration via the original tables:
           - only actions available prior to introduction of
             tIPvXFltrEntryActionTable are allowed:
             When an entry is created in tIPFilterParamsTable then an entry with
             the value of tIPvXFltrEntryActActionId equal to 'primary' and the
             value of tIPvXFltrEntryActFltrType equal to 'fltrtypeselIp' is
             created in tIPvXFltrEntryActionTable by the system.  When an entry
             is created in tIPv6FilterParamsTable then an entry with the value
             of tIPvXFltrEntryActActionId equal to 'primary' and the value of
             tIPvXFltrEntryActFltrType equal to 'fltrtypeselIpv6' is created in
             tIPvXFltrEntryActionTable by the system. This new system created
             entry in tIPvXFltrEntryActionTable will contain interpretation of
             values pertaining to configured action in tIPFilterParamsEntry or
             tIPv6FilterParamsEntry and their augment tables.

         Configuration via tIPvXFltrEntryActionTable:
           - action available prior to introduction of
             tIPvXFltrEntryActionTable:
             If an action which was available prior to introduction of
             tIPvXFltrEntryActionTable is configured via
             tIPvXFltrEntryActionTable and the value of
             tIPvXFltrEntryActActionId for that action is equal to 'primary'
             then the action related objects in the original tables will be
             automatically set by the system to the interpretation of the values
             in tIPvXFltrEntryActionTable pertaining to that action.

           - action not available prior to introduction of
             tIPvXFltrEntryActionTable:
             If an action not available prior to introduction of
             tIPvXFltrEntryActionTable is configured via
             tIPvXFltrEntryActionTable then the value of tIPFilterParamsAction
             (in case of IPv4 filter) or tIPv6FilterParamsAction (in case of
             IPv6 filter) is set to 'unrecognized' by the system. The value
             'unrecognized' indicates that the functionality not supported by
             the original tables was configured and therefore action related
             objects in the original tables are not valid and shouldn't be used
             for configuration."
   ::= { tFilterObjects 85 }

tIPvXFltrEntryActionEntry OBJECT-TYPE
    SYNTAX      TIPvXFltrEntryActionEntry
    MAX-ACCESS  not-accessible
    STATUS      current
    DESCRIPTION
        "The entry contains information pertaining to an action for a particular
         IPv4 or IPv6 filter entry (information pertaining to IPv4 filter
         entry is in tIPFilterParamsTable and tIPFilterParamsExtTable and
         information pertaining to IPv6 filter entry is in
         tIPv6FilterParamsTable and tIPv6FilterParamsExtTable). Per one filter
         entry up to two actions can be configured (primary and secondary).

         Entries with the value of tIPvXFltrEntryActActionId equal to 'primary'
         are created and destroyed by SNMP SET operations on the object
         tIPFilterParamsRowStatus or tIPv6FilterParamsRowStatus. Entries with
         the value of tIPvXFltrEntryActActionId equal to 'secondary' are created
         by SNMP SET operation on the object tIPvXFltrEntryActRowStatus and
         destroyed by SNMP SET operation on the object
         tIPvXFltrEntryActRowStatus, tIPFilterParamsRowStatus or
         tIPv6FilterParamsRowStatus."
    INDEX { tIPvXFltrEntryActFltrType, tIPvXFltrEntryActFltrId,
            tIPvXFltrEntryActEntryId, tIPvXFltrEntryActActionId }
    ::= { tIPvXFltrEntryActionTable 1 }

TIPvXFltrEntryActionEntry ::= SEQUENCE
    {
        tIPvXFltrEntryActFltrType            TFilterType,
        tIPvXFltrEntryActFltrId              TAnyFilterID,
        tIPvXFltrEntryActEntryId             TAnyEntryId,
        tIPvXFltrEntryActActionId            TFilterEntryActionId,
        tIPvXFltrEntryActLastChanged         TimeStamp,
        tIPvXFltrEntryActRowStatus           RowStatus,
        tIPvXFltrEntryActAction              TIPvXFilterEntryAction,
        tIPvXFltrEntryActFwdNHIpAddrType     InetAddressType,
        tIPvXFltrEntryActFwdNHIpAddr         InetAddress,
        tIPvXFltrEntryActFwdNHIndirect       TruthValue,
        tIPvXFltrEntryActFwdNHInterface      TNamedItemOrEmpty,
        tIPvXFltrEntryActFwdRedPlcy          TNamedItemOrEmpty,
        tIPvXFltrEntryActFwdSapPortId        TmnxPortID,
        tIPvXFltrEntryActFwdSapEncapVal      TmnxEncapVal,
        tIPvXFltrEntryActFwdSdpBind          SdpBindId,
        tIPvXFltrEntryActRedirectURL         TmnxHttpRedirectUrl,
        tIPvXFltrEntryActRdirAllwRadOvr      TruthValue,
        tIPvXFltrEntryActFwdRtrId            TmnxVRtrIDOrZero,
        tIPvXFltrEntryActNatPolicyName       TNamedItemOrEmpty,
        tIPvXFltrEntryActNatType             TmnxNatSubscriberTypeOrNone,
        tIPvXFltrEntryActFwdLsp              TmnxVRtrMplsLspID,
        tIPvXFltrEntryActFwdLspRtrId         TmnxVRtrIDOrZero,
        tIPvXFltrEntryActPktLenVal1          TFilterPacketLength,
        tIPvXFltrEntryActPktLenVal2          TFilterPacketLength,
        tIPvXFltrEntryActPktLenOper          TOperator,
        tIPvXFltrEntryActTTLVal1             TFilterTTL,
        tIPvXFltrEntryActTTLVal2             TFilterTTL,
        tIPvXFltrEntryActTTLOper             TOperator,
        tIPvXFltrEntryActEsi                 TFilterEsi,
        tIPvXFltrEntryActFwdEsiSvcId         TmnxServId,
        tIPvXFltrEntryActFwdEsiVRtrId        TmnxVRtrIDOrZero,
        tIPvXFltrEntryActFwdEsiSFIpType      InetAddressType,
        tIPvXFltrEntryActFwdEsiSFIp          InetAddress,
        tIPvXFltrEntryActFwdEsiVasIf         InterfaceIndexOrZero,
        tIPvXFltrEntryActRateLimit           TFilterEntryActionRateLimit,
        tIPvXFltrEntryActPbrTargetStatus     TFilterPbrTargetStatus,
        tIPvXFltrEntryActRemarkDSCP          TDSCPNameOrEmpty,
        tIPvXFltrEntryActActionExt           TIPvXFilterEntryActionExt
 }

tIPvXFltrEntryActFltrType OBJECT-TYPE
    SYNTAX      TFilterType
    MAX-ACCESS  not-accessible
    STATUS      current
    DESCRIPTION
        "The value of the object tIPvXFltrEntryActFltrType specifies the type
         of the filter to which this action belongs.

         Only values 'fltrtypeselIp' and 'fltrtypeselIpv6' are supported.

         Refer to the description of the textual convention TFilterType
         for more information."
    ::= { tIPvXFltrEntryActionEntry 1 }

tIPvXFltrEntryActFltrId OBJECT-TYPE
    SYNTAX      TAnyFilterID
    MAX-ACCESS  not-accessible
    STATUS      current
    DESCRIPTION
        "The value of the object tIPvXFltrEntryActFltrId specifies the filter
         id of the filter to which this action belongs. The filter must exist in
         tIPFilterTable, if the value of tIPvXFltrEntryActFltrType is 'ipv4' or
         it must exist in tIPv6FilterTable if the value of
         tIPvXFltrEntryActFltrType is 'ipv6'.

         Refer to the description of the textual convention TAnyFilterID
         for more information."
    ::= { tIPvXFltrEntryActionEntry 2 }

tIPvXFltrEntryActEntryId OBJECT-TYPE
    SYNTAX      TAnyEntryId
    MAX-ACCESS  not-accessible
    STATUS      current
    DESCRIPTION
        "The value of the object tIPvXFltrEntryActEntryId specifies the entry id
         of the entry to which this filter action belongs. The filter entry must
         exist in tIPFilterParamsTable, if the value of
         tIPvXFltrEntryActFltrType is 'ipv4' or it must exist in
         tIPv6FilterParamsTable if the value of tIPvXFltrEntryActFltrType is
         'ipv6'.

         Refer to the description of the textual convention TAnyEntryId
         for more information."
    ::= { tIPvXFltrEntryActionEntry 3 }

tIPvXFltrEntryActActionId OBJECT-TYPE
    SYNTAX      TFilterEntryActionId
    MAX-ACCESS  not-accessible
    STATUS      current
    DESCRIPTION
        "The value of the object tIPvXFltrEntryActActionId specifies a unique
         identifier of an action within the filter entry. Per one filter entry
         up to two actions can be configured (the primary and the secondary).
         Destination availability checking is turned on when both actions (the
         primary and the secondary) are configured for an entry. This is allowed
         only for the following combinations of actions:
            - both actions are PBF to SAP
            - both actions are PBF to SDP
            - the primary action is PBF to SAP and the secondary action is
              forward SDP or vice-versa
            - both actions are PBR to next-hop router

         If the PBR/PBF destination of the primary action is available, then the
         primary action will be taken on a packet matching the filter entry. If
         the PBR/PBF destination of the primary action is not available and the
         PBR/PBF destination of the secondary action is available then the
         secondary action will be taken on a packet matching the filter entry.
         If none of the actions for the entry has an available PBR/PBF
         destination then the action specified by the object
         tIPFilterParamsExtPbrDwnActOvr(for IPv4 filters) or
         tIPv6FilterParamsExtPbrDwnActOvr(for IPv6 filters) will be taken on
         a packet matching the filter entry.

         There is a limit to the number of entries with the destination
         availability checking turned on."
    ::= { tIPvXFltrEntryActionEntry 4 }

tIPvXFltrEntryActLastChanged OBJECT-TYPE
    SYNTAX      TimeStamp
    MAX-ACCESS  read-only
    STATUS      current
    DESCRIPTION
        "The value of the object tIPvXFltrEntryActLastChanged indicates the
         sysUpTime at the time of the last modification of
         tIPvXFltrEntryActionEntry.

         If no changes were made to the entry since the last re-initialization
         of the local network management subsystem, then this object contains
         a zero value."
    ::= { tIPvXFltrEntryActionEntry 5 }

tIPvXFltrEntryActRowStatus OBJECT-TYPE
    SYNTAX      RowStatus
    MAX-ACCESS  read-create
    STATUS      current
    DESCRIPTION
        "The value of the object tIPvXFltrEntryActRowStatus specifies
         the status of the conceptual row in tIPvXFltrEntryActionTable.

         Rows with the value of tIPvXFltrEntryActActionId equal to 'primary' are
         created and destroyed by SNMP SET operations on the object
         tIPFilterParamsRowStatus or tIPv6FilterParamsRowStatus. Rows with the
         value of tIPvXFltrEntryActActionId equal to 'secondary' are created by
         SNMP SET operation on the object tIPvXFltrEntryActRowStatus and
         destroyed by SNMP SET operation on the object
         tIPvXFltrEntryActRowStatus, tIPFilterParamsRowStatus or
         tIPv6FilterParamsRowStatus."
    ::= { tIPvXFltrEntryActionEntry 6 }

tIPvXFltrEntryActAction OBJECT-TYPE
    SYNTAX      TIPvXFilterEntryAction
    MAX-ACCESS  read-create
    STATUS      current
    DESCRIPTION
        "The value of the object tIPvXFltrEntryActAction specifies the action
         to be taken on a packet matching the filter entry.

         Refer to the description of the textual convention
         TIPvXFilterEntryAction for more information."
    DEFVAL { drop }
    ::= { tIPvXFltrEntryActionEntry 7 }

tIPvXFltrEntryActFwdNHIpAddrType OBJECT-TYPE
    SYNTAX      InetAddressType
    MAX-ACCESS  read-create
    STATUS      current
    DESCRIPTION
        "The value of the object tIPvXFltrEntryActFwdNHIpAddrType specifies the
         context in which the value of the object tIPvXFltrEntryActFwdNHIpAddr
         is interpreted.

         Only following values are supported:
            unknown(0)
            ipv4(1)
            ipv6(2)
         
         The value of tIPvXFltrEntryActFwdNHIpAddrType must be consistent with
         the value of tIPvXFltrEntryActFltrType.
         
         Note that the value of tIPvXFltrEntryActFwdNHIpAddrType is silently
         cleared by the system if tIPvXFltrEntryActAction is set to value other
         than 'forwardNextHop' or 'forwardNextHopRtr'."
    DEFVAL { unknown }
    ::= { tIPvXFltrEntryActionEntry 8 }


tIPvXFltrEntryActFwdNHIpAddr OBJECT-TYPE
    SYNTAX      InetAddress (SIZE (0|4|16))
    MAX-ACCESS  read-create
    STATUS      current
    DESCRIPTION
        "The value of the object tIPvXFltrEntryActFwdNHIpAddr specifies the
         IP/IPv6 address of the nexthop to which the packet should be forwarded
         if it hits this filter entry. The action of this entry should be
         'forwardNextHop' or 'forwardNextHopRtr' in such a case.

         Note that the value of tIPvXFltrEntryActFwdNHIpAddr is silently cleared
         by the system if tIPvXFltrEntryActAction is set to value other than
         'forwardNextHop' or 'forwardNextHopRtr'."
    DEFVAL { '00000000000000000000000000000000'H }
    ::= { tIPvXFltrEntryActionEntry 9 }

tIPvXFltrEntryActFwdNHIndirect OBJECT-TYPE
    SYNTAX      TruthValue
    MAX-ACCESS  read-create
    STATUS      current
    DESCRIPTION
        "The value of the object tIPvXFltrEntryActFwdNHIndirect specifies if
         the nexthop is directly or indirectly reachable. The action of this
         entry should be 'forwardNextHop' or 'forwardNextHopRtr' in such a case.

         Note that the value of tIPvXFltrEntryActFwdNHIndirect is silently
         cleared by the system if tIPvXFltrEntryActAction is set to value
         other than 'forwardNextHop' or 'forwardNextHopRtr'."
    DEFVAL { false }
    ::= { tIPvXFltrEntryActionEntry 10 }

tIPvXFltrEntryActFwdNHInterface OBJECT-TYPE
    SYNTAX      TNamedItemOrEmpty
    MAX-ACCESS  read-create
    STATUS      current
    DESCRIPTION
        "The value of the object tIPvXFltrEntryActFwdNHInterface specifies the
         interface name for the nexthop to which the packet should be forwarded
         if it hits this filter entry. The action of this entry should be
         'forwardNHInterface' in such a case.

         Note that the value of tIPvXFltrEntryActFwdNHInterface  is silently
         cleared by the system if tIPvXFltrEntryActAction is set to value
         other than 'forwardNHInterface'."
    DEFVAL { ''H }
    ::= { tIPvXFltrEntryActionEntry 11 }

tIPvXFltrEntryActFwdRedPlcy OBJECT-TYPE
    SYNTAX      TNamedItemOrEmpty
    MAX-ACCESS  read-create
    STATUS      current
    DESCRIPTION
        "The value of the object tIPvXFltrEntryActFwdRedPlcy specifies the
         redirect policy to be used to determine the nexthop. The action of this
         entry should be 'forwardRPlcy' in such a case.

         Note that the value of tIPvXFltrEntryActFwdRedPlcy is silently cleared
         by the system if tIPvXFltrEntryActAction is set to value other than
         'forwardRPlcy'."
    DEFVAL { ''H }
    ::= { tIPvXFltrEntryActionEntry 12 }

tIPvXFltrEntryActFwdSapPortId OBJECT-TYPE
    SYNTAX      TmnxPortID
    MAX-ACCESS  read-create
    STATUS      current
    DESCRIPTION
        "The value of the object tIPvXFltrEntryActFwdSapPortId specifies the
         sap port id of the destination for this filter entry.

         The value 0 indicates that there is no SAP destination defined. A value
         different from 0 can only be specified if the value of the
         tIPvXFltrEntryActAction object of this entry is 'forwardSap'.  In
         addition a non-zero value can only be given if the object
         tIPvXFltrEntryActFwdSdpBind is '0'.

         Note that the value of tIPvXFltrEntryActFwdSapPortId is silently
         cleared by the system if tIPvXFltrEntryActAction is set to value
         other than 'forwardSap'."
    DEFVAL { 0 }
    ::= { tIPvXFltrEntryActionEntry 13 }

tIPvXFltrEntryActFwdSapEncapVal OBJECT-TYPE
    SYNTAX      TmnxEncapVal
    MAX-ACCESS  read-create
    STATUS      current
    DESCRIPTION
        "The value of the object tIPvXFltrEntryActFwdSapEncapVal specifies the
         sap port encap value of the destination SAP for this filter entry.

         A value different from 0 can only be specified if the value of the
         tIPvXFltrEntryActAction object of this entry is 'forwardSap'. In
         addition a non-zero value can only be given if the object
         tIPvXFltrEntryActFwdSdpBind has value '0'.
         The value 0 indicates that either
         1) the sap encapsulation value is not specified when
            tIPvXFltrEntryActFwdSapPortId and based on the filter type
            tIPFilterParamsFwdSvcId or tIPv6FilterParamsFwdSvcId have valid
            values; or
         2) that there is no SAP destination.

         Note that the value of tIPvXFltrEntryActFwdSapEncapVal is silently
         cleared by the system if tIPvXFltrEntryActAction is set to value
         other than 'forwardSap'."
    DEFVAL { 0 }
    ::= { tIPvXFltrEntryActionEntry 14 }

tIPvXFltrEntryActFwdSdpBind OBJECT-TYPE
    SYNTAX      SdpBindId
    MAX-ACCESS  read-create
    STATUS      current
    DESCRIPTION
        "The value of the object tIPvXFltrEntryActFwdSdpBind specifies the sdp
         bind id of the destination for this filter entry.

         The value '0' indicates that there is currently no SDP binding defined.
         A value different from '0' can only be specified if the value of the
         tIPvXFltrEntryActAction object of this entry is 'forwardSdp'. In
         addition a non-zero value can only be given if the objects
         tIPvXFltrEntryActFwdSapPortId and tIPvXFltrEntryActFwdSapEncapVal
         have value 0.

         Note that the value of tIPvXFltrEntryActFwdSdpBind is silently cleared
         by the system if tIPvXFltrEntryActAction is set to value other than
         'forwardSdp', or any object related to 'forward' other than this one
         is set."
    DEFVAL { '0000000000000000'H }
    ::= { tIPvXFltrEntryActionEntry 15 }

tIPvXFltrEntryActRedirectURL OBJECT-TYPE
    SYNTAX      TmnxHttpRedirectUrl
    MAX-ACCESS  read-create
    STATUS      current
    DESCRIPTION
        "The value of the object tIPvXFltrEntryActRedirectURL specifies the URL
         to redirect to, when the value of tIPvXFltrEntryActAction is
         'httpRedirect'.

         The following macro substitutions are applicable in this context:
         $URL, $MAC, $IP, $SUB, $SAP, $SAPDESC, $CID, and $RID.

         Note that the value of tIPvXFltrEntryActRedirectURL is silently
         cleared by the system if tIPvXFltrEntryActAction is set to any value
         other than 'httpRedirect'."
    DEFVAL { ''H }
    ::= { tIPvXFltrEntryActionEntry 16 }

tIPvXFltrEntryActRdirAllwRadOvr OBJECT-TYPE
    SYNTAX      TruthValue
    MAX-ACCESS  read-create
    STATUS      current
    DESCRIPTION
        "The value of the object tIPvXFltrEntryActRdirAllwRadOvr specifies
         whether or not the value of tIPvXFltrEntryActRedirectURL can be
         over-ridden by a Radius VSA. The default value is false (i.e. the URL
         cannot be over-ridden by Radius).  The value of
         tIPvXFltrEntryActRdirAllwRadOvr is relevant only if the value of
         tIPvXFltrEntryActAction is 'httpRedirect'.

         The value of tIPvXFltrEntryActRdirAllwRadOvr can't be set to true if
         the value of tIPvXFltrEntryActAction is not 'httpRedirect'.
         Furthermore, the value of tIPvXFltrEntryActRdirAllwRadOvr is silently
         reset to false by the system if tIPvXFltrEntryActAction is set to any
         value other than 'httpRedirect'."
    DEFVAL { false }
    ::= { tIPvXFltrEntryActionEntry 17 }

tIPvXFltrEntryActFwdRtrId OBJECT-TYPE
    SYNTAX      TmnxVRtrIDOrZero
    MAX-ACCESS  read-create
    STATUS      current
    DESCRIPTION
        "The value of the object tIPvXFltrEntryActFwdRtrId specifies, if
         different from '0', the routing context in which the packet will be
         forwarded if it hits this filter entry.

         The action of this entry should be 'forwardRtr' or 'forwardNextHopRtr'
         in such a case.

         Note that the value of tIPvXFltrEntryActFwdRtrId is silently cleared
         by the system if tIPvXFltrEntryActAction is set to value other than
         'forwardRtr' or 'forwardNextHopRtr'."
    DEFVAL { 0 }
    ::= { tIPvXFltrEntryActionEntry 18 }

tIPvXFltrEntryActNatPolicyName OBJECT-TYPE
    SYNTAX      TNamedItemOrEmpty
    MAX-ACCESS  read-create
    STATUS      current
    DESCRIPTION
        "The value of the object tIPvXFltrEntryActNatPolicyName specifies the
         name of the NAT policy to be used when the value of
         tIPvXFltrEntryActAction is 'nat'. If the value is empty then
         a default policy is used. If the value is non-empty then it must
         correspond to a policy defined in tmnxNatPlcyTable.

         The value of tIPvXFltrEntryActNatPolicyName is relevant only if the
         value of tIPvXFltrEntryActAction is 'nat'. Setting the value of
         tIPvXFltrEntryActNatPolicyName to a non-empty string is allowed only
         if the value of tIPvXFltrEntryActAction is 'nat'.

         Furthermore, the value of tIPvXFltrEntryActNatPolicyName is silently
         reset to an empty string by the system if tIPvXFltrEntryActAction is
         set to any value other than 'nat'."
    DEFVAL { "" }
    ::= { tIPvXFltrEntryActionEntry 19 }

tIPvXFltrEntryActNatType OBJECT-TYPE
    SYNTAX TmnxNatSubscriberTypeOrNone {
        none          (0),
        dsliteLsnSub  (3),
        nat64LsnSub   (4)
    }
    MAX-ACCESS read-create
    STATUS current
    DESCRIPTION
        "The value of the object tIPvXFltrEntryActNatType specifies the NAT type
         to be used when the value of tIPvXFltrEntryActAction is 'nat'.

         The object tIPvXFltrEntryActNatType is applicable only for IPv6
         filters. The only supported value for ipv4 filters is value 'none'.

         Note that the value of tIPvXFltrEntryActNatType is silently cleared
         by the system if tIPvXFltrEntryActAction is set to value other than
         'nat'."
    DEFVAL { dsliteLsnSub }
    ::= { tIPvXFltrEntryActionEntry 20 }

tIPvXFltrEntryActFwdLsp OBJECT-TYPE
    SYNTAX      TmnxVRtrMplsLspID
    MAX-ACCESS  read-create
    STATUS      current
    DESCRIPTION
         "The value of the object tIPvXFltrEntryActFwdLsp if different from '0'
          together with the value of the object tIPvXFltrEntryActFwdLspRtrId
          specifies the LSP into which a packet should be forwarded if it hits
          this filter entry.

          The value of the object tIPvXFltrEntryActAction of this entry
          must be 'forwardLsp' in such case.

          The value is reset to '0' if the value of the object
          tIPvXFltrEntryActAction is set to value other than 'forwardLsp'.

          The value has to be '0' if the value of the object
          tIPvXFltrEntryActFwdLspRtrId is not set (i.e. is '0').

          If a non-zero value is set, the value of the object
          tIPvXFltrEntryActFwdLspRtrId has to be set as well."
    DEFVAL { 0 }
    ::= { tIPvXFltrEntryActionEntry 21 }

tIPvXFltrEntryActFwdLspRtrId OBJECT-TYPE
    SYNTAX      TmnxVRtrIDOrZero
    MAX-ACCESS  read-create
    STATUS      current
    DESCRIPTION
         "The value of the object tIPvXFltrEntryActFwdLspRtrId specifies
          the router ID that the LSP ID defined by the value of the object
          tIPvXFltrEntryActFwdLsp belongs to.

          The value of the object tIPvXFltrEntryActAction of this entry
          must be 'forwardLsp' in such case.

          The value is reset to '0' if the value of the object
          tIPvXFltrEntryActAction is set to other value than 'forwardLsp'.

          The value has to be '0' if the value of the object
          tIPvXFltrEntryActFwdLsp is not set (i.e. is '0').

          If a non-zero value is set, the value of the object
          tIPvXFltrEntryActFwdLsp has to be set as well.

          The ID of the base router and '0' are the only allowed values
          with this version of the product."
    DEFVAL { 0 }
    ::= { tIPvXFltrEntryActionEntry 22 }

tIPvXFltrEntryActPktLenVal1 OBJECT-TYPE
    SYNTAX      TFilterPacketLength
    MAX-ACCESS  read-create
    STATUS      current
    DESCRIPTION
        "The value of the object tIPvXFltrEntryActPktLenVal1 specifies the
         value1 to be compared to the value of 'Total Length' field of IPv4
         header or 'Payload Length' field of IPv6 header of an IP packet that
         has hit this filter's entry.

         The way how the value of this object is used depends on the value
         of the object tIPvXFltrEntryActPktLenOper.

         The value of this object can be set to a non-default value only
         if the value of the object tIPvXFltrEntryActPktLenOper is other
         than 'none (0)'.

         If the value of tIPvXFltrEntryActPktLenOper is 'range (2)' then
         the value of this object must be less than the value
         of tIPvXFltrEntryActPktLenVal2.

         If the value of tIPvXFltrEntryActPktLenOper is 'lt (3)' then
         the value of this object can be set in range 1..65535.

         If the value of tIPvXFltrEntryActPktLenOper is 'gt (4)' then
         the value of this object can be set in range 0..65534.

         If both the values of the objects tIPvXFltrEntryActPktLenOper and
         tIPvXFltrEntryActPktLenVal1 need to be changed then it must be
         done in the same SET SNMP request.

         Note that the value of this object is silently cleared by the system
         if tIPvXFltrEntryActAction is set to a value other than 'dropPktLen'
         or
         if tIPvXFltrEntryActPktLenOper is set to 'none (0)'
         or
         if tIPvXFltrEntryActTTLOper is set to a value other
         than 'none (0)'. "
    DEFVAL { 0 }
    ::= { tIPvXFltrEntryActionEntry 23 }

tIPvXFltrEntryActPktLenVal2 OBJECT-TYPE
    SYNTAX      TFilterPacketLength
    MAX-ACCESS  read-create
    STATUS      current
    DESCRIPTION
        "The value of the object tIPvXFltrEntryActPktLenVal2 specifies the
         value2 to be compared to the value of 'Total Length' field of IPv4
         header or 'Payload Length' field of IPv6 header of an IP packet that
         has hit this filter's entry.

         The way how the value of this object is used depends on the value
         of the object tIPvXFltrEntryActPktLenOper.

         The value of this object can be set to a non-default value only
         if the value of the object tIPvXFltrEntryActPktLenOper is 'range (2)'.

         The value of this object must be greater than the value
         of tIPvXFltrEntryActPktLenVal1.

         If both the values of the objects tIPvXFltrEntryActPktLenOper and
         tIPvXFltrEntryActPktLenVal2 need to be changed then it must be
         done in the same SET SNMP request.

         Note that the value of this object is silently cleared by the system
         if tIPvXFltrEntryActAction is set to a value other than 'dropPktLen'
         or
         if tIPvXFltrEntryActPktLenOper is set to value other than
         'range (2)'
         or
         if tIPvXFltrEntryActTTLOper is set to a value other
         than 'none (0)'.
         "
    DEFVAL { 0 }
    ::= { tIPvXFltrEntryActionEntry 24 }

tIPvXFltrEntryActPktLenOper OBJECT-TYPE
    SYNTAX      TOperator
    MAX-ACCESS  read-create
    STATUS      current
    DESCRIPTION
        "The value of the object tIPvXFltrEntryActPktLenOper specifies the way
         how the values of the objects tIPvXFltrEntryActPktLenVal1 and
         tIPvXFltrEntryActPktLenVal2 are used to form a condition that must be
         fulfilled in order to execute the action specified by the value of
         tIPvXFltrEntryActAction. Otherwise the opposite action is executed.

         The value of this object can be set to a non-default value only if
         the value of the object tIPvXFltrEntryActAction is 'drop (1)'.

         If the value of this object is being changed from the default value
         to any non-default value the values of the objects
         tIPvXFltrEntryActPktLenVal1 and tIPvXFltrEntryActPktLenVal2
         (if applicable) must be sent in the same SET SNMP request.

         If the value of this object is 'none (0)' than the values of
         the objects tIPvXFltrEntryActPktLenVal1 and
         tIPvXFltrEntryActPktLenVal2 are ignored and TRUE case action is
         always executed (see table below).

         If the value of this object is 'eq (1)' then the value of the Total
         Length field of the IP header of the packet that has matched this
         filter's entry must be equal to the value of the object
         tIPvXFltrEntryActPktLenVal1 in order to execute the TRUE case action
         (see table below). Otherwise the FALSE case action is executed.
         The value of the object tIPvXFltrEntryActPktLenVal2 is ignored.

         If the value of this object is 'range (2)' then the value of the Total
         Length field of the IP header of the packet that has matched this
         filter's entry must be greater than or equal to the value of the object
         tIPvXFltrEntryActPktLenVal1 and less than or equal to the value
         of the object tIPvXFltrEntryActPktLenVal2 in order to execute
         the TRUE case action (see table below). Otherwise the FALSE case action
         is executed.

         If the value of this object is 'lt (3)' then the value of the Total
         Length field of the IP header of the packet that has matched this
         filter's entry must be less than the value of the object
         tIPvXFltrEntryActPktLenVal1 in order to execute the TRUE case action
         (see table below). Otherwise the FALSE case action is executed.
         The value of the object tIPvXFltrEntryActPktLenVal2 is ignored.

         If the value of this object is 'gt (4)' then the value of the Total
         Length field of the IP header of the packet that has matched this
         filter's entry must be greater than the value of the object
         tIPvXFltrEntryActPktLenVal1 in order to execute the TRUE case action
         (see table below). Otherwise the FALSE case action is executed.
         The value of the object tIPvXFltrEntryActPktLenVal2 is ignored.


         tIPvXFltrEntryActAction |   TRUE case action  |  FALSE case action
         ------------------------------------------------------------------
         drop                      |      drop           |      forward


         Allowed ranges for the values of tIPvXFltrEntryActPktLenVal1 and
         tIPvXFltrEntryActPktLenVal2 are:

         Operator                |Packet Length Value 1|Packet Length Value 2
         --------------------------------------------------------------------
         none (0)                |      N/A            |      N/A
         eq(1)                   |    0..65535         |      N/A
         range(2)                |    0..65534         | (Value1 + 1)..65535
         lt(3)                   |    1..65535         |      N/A
         gt(4)                   |    0..65534         |      N/A


         The values of the objects tIPvXFltrEntryActPktLenVal1 and
         tIPvXFltrEntryActPktLenVal2 are silently cleared if the value of this
         object is set to default.

         Note that the value of this object is silently cleared by the system
         if tIPvXFltrEntryActAction is set to a value other than 'dropPktLen'
         or
         if tIPvXFltrEntryActTTLOper is set to a value other than 'none (0)'.
         "
    DEFVAL { none }
    ::= { tIPvXFltrEntryActionEntry 25 }

tIPvXFltrEntryActTTLVal1 OBJECT-TYPE
    SYNTAX      TFilterTTL
    MAX-ACCESS  read-create
    STATUS      current
    DESCRIPTION
        "The value of the object tIPvXFltrEntryActTTLVal1 specifies the value1
         to be compared to the value of 'Time-to-live' field of IPv4 header or
         'Hop-Limit' field of IPv6 header of an IP packet that has hit this
         filter's entry.

         The way how the value of this object is used depends on the value
         of the object tIPvXFltrEntryActTTLOper.

         The value of this object can be set to a non-default value only
         if the value of the object tIPvXFltrEntryActTTLOper is other
         than 'none (0)'.

         If the value of tIPvXFltrEntryActTTLOper is 'range (2)' then
         the value of this object must be less than the value
         of tIPvXFltrEntryActTTLVal2.

         If the value of tIPvXFltrEntryActTTLOper is 'lt (3)' then
         the value of this object can be set in range 1..255.

         If the value of tIPvXFltrEntryActTTLOper is 'gt (4)' then
         the value of this object can be set in range 0..254.

         If both the values of the objects tIPvXFltrEntryActTTLOper and
         tIPvXFltrEntryActTTLVal1 need to be changed then it must be
         done in the same SET SNMP request.

         Note that the value of this object is silently cleared by the system
         if tIPvXFltrEntryActAction is set to a value other than 'dropTtl'
         or
         if tIPvXFltrEntryActTTLOper is set to 'none (0)'
         or
         if tIPvXFltrEntryActPktLenOper is set to a value other
         than 'none (0)'."
    DEFVAL { 0 }
    ::= { tIPvXFltrEntryActionEntry 26 }

tIPvXFltrEntryActTTLVal2 OBJECT-TYPE
    SYNTAX      TFilterTTL
    MAX-ACCESS  read-create
    STATUS      current
    DESCRIPTION
        "The value of the object tIPvXFltrEntryActTTLVal2 specifies value2
         to be compared to the value of 'Time-to-live' field of IPv4 header or
         'Hop-Limit' field of IPv6 header of an IP packet that has hit this
         filter's entry.

         The way how the value of this object is used depends on the value
         of the object tIPvXFltrEntryActTTLOper.

         The value of this object can be set to a non-default value only
         if the value of the object tIPvXFltrEntryActTTLOper is 'range (2)'.

         The value of this object must be greater than the value
         of tIPvXFltrEntryActTTLVal1.

         If both the values of the objects tIPvXFltrEntryActTTLOper and
         tIPvXFltrEntryActTTLVal2 need to be changed then it must be
         done in the same SET SNMP request.

         Note that the value of this object is silently cleared by the system
         if tIPvXFltrEntryActAction is set to a value other than 'dropTtl'
         or
         if tIPvXFltrEntryActTTLOper is set to a value other than
         'range (2)'
         or
         if tIPvXFltrEntryActPktLenOper is set to a value other than
         'none (0)'."
    DEFVAL { 0 }
    ::= { tIPvXFltrEntryActionEntry 27 }

tIPvXFltrEntryActTTLOper OBJECT-TYPE
    SYNTAX      TOperator
    MAX-ACCESS  read-create
    STATUS      current
    DESCRIPTION
        "The value of the object tIPvXFltrEntryActTTLOper specifies the way how
         the values of the objects tIPvXFltrEntryActTTLVal1 and
         tIPvXFltrEntryActTTLVal2 are used to form a condition that must be
         fulfilled in order to execute the action specified by the value of
         tIPvXFltrEntryActAction. Otherwise the opposite action is executed.

         The value of this object can be set to a non-default value only if
         the value of the object tIPvXFltrEntryActAction is 'drop (1)'.

         If the value of this object is being changed from the default value
         to any non-default value the values of the objects
         tIPvXFltrEntryActTTLVal1 and tIPvXFltrEntryActTTLVal2
         (if applicable) must be sent in the same SET SNMP request.

         If the value of this object is 'none (0)' than the values of
         the objects tIPvXFltrEntryActTTLVal1 and
         tIPvXFltrEntryActTTLVal2 are ignored and TRUE case action is
         always executed (see table below).

         If the value of this object is 'eq (1)' then the value of
         the Time-To-Live field of the IP header of the packet that has matched
         this filter's entry must be equal to the value of the object
         tIPvXFltrEntryActTTLVal1 in order to execute the TRUE case action
         (see table below). Otherwise the FALSE case action is executed.
         The value of the object tIPvXFltrEntryActTTLVal2 is ignored.

         If the value of this object is 'range (2)' then the value of
         the Time-To-Live field of the IP header of the packet that has matched
         this filter's entry must be greater than or equal to the value of
         the object tIPvXFltrEntryActTTLVal1 and less than or equal to
         the value of the object tIPvXFltrEntryActTTLVal2 in order to execute
         the TRUE case action (see table below). Otherwise the FALSE case
         action is executed.

         If the value of this object is 'lt (3)' then the value of
         the Time-To-Live field of the IP header of the packet that has matched
         this filter's entry must be less than the value of the object
         tIPvXFltrEntryActTTLVal1 in order to execute the TRUE case action
         (see table below). Otherwise the FALSE case action is executed.
         The value of the object tIPvXFltrEntryActTTLVal2 is ignored.

         If the value of this object is 'gt (4)' then the value of
         the Time-To-Live field of the IP header of the packet that has matched
         this filter's entry must be greater than the value of the object
         tIPvXFltrEntryActTTLVal1 in order to execute the TRUE case action
         (see table below). Otherwise the FALSE case action is executed.
         The value of the object tIPvXFltrEntryActTTLVal2 is ignored.


         tIPvXFltrEntryActAction |   TRUE case action  |  FALSE case action
         ------------------------------------------------------------------
         drop                      |      drop           |      forward


         Allowed ranges for the values of tIPvXFltrEntryActTTLVal1 and
         tIPvXFltrEntryActTTLVal2 are:

         Operator                | Time-To-Live Value 1| Time-To-Live Value 2
         --------------------------------------------------------------------
         none (0)                |      N/A            |      N/A
         eq(1)                   |    0..255           |      N/A
         range(2)                |    0..254           | (Value1 + 1)..255
         lt(3)                   |    1..255           |      N/A
         gt(4)                   |    0..254           |      N/A


         The values of the objects tIPvXFltrEntryActTTLVal1 and
         tIPvXFltrEntryActTTLVal2 are silently cleared if the value of this
         object is set to default.

         Note that the value of this object is silently cleared by the system
         if tIPvXFltrEntryActAction is set to a value other than 'dropTtl'
         or
         if tIPvXFltrEntryActPktLenOper is set to a value other than
         'none (0)'."
    DEFVAL { none }
    ::= { tIPvXFltrEntryActionEntry 28 }

tIPvXFltrEntryActEsi OBJECT-TYPE
    SYNTAX      TFilterEsi
    MAX-ACCESS  read-create
    STATUS      current
    DESCRIPTION
        "The value of the object tIPvXFltrEntryActEsi specifies the ethernet
         segment identifier (ESI) of the first ESI identified appliance in Nuage
         service chain. When the value of tMacFilterParamsAction is
         'forwardEsiL2' or 'forwardEsiL3' packets matching the filter entry are
         forwarded to the appliance using EVPN-resolved VXLAN tunnel in the
         specified VPLS/VPRN service
         (tIPvXFltrEntryActFwdEsiSvcId/tIPvXFltrEntryActFwdEsiVRtrId).

         The value '0' indicates that there is no ESI specified.

         There are two options how to set the value of tIPvXFltrEntryActEsi:
         1. Non zero value of tIPvXFltrEntryActEsi is set together
            with non zero values of tIPvXFltrEntryActFwdEsiVRtrId,
            tIPvXFltrEntryActFwdEsiSFIpType and tIPvXFltrEntryActFwdEsiSFIp.
            In this case value of tIPvXFltrEntryActAction is set to
            'forwardEsiL3' by the system.

         2. Non zero value of tIPvXFltrEntryActEsi is set together with a non
            zero value of tIPvXFltrEntryActFwdEsiSvcId. In this case value of
            tIPvXFltrEntryActAction is set to 'forwardEsiL2' by the system.

         Note that the value of tIPvXFltrEntryActEsi is silently cleared by the
         system if the value of tIPvXFltrEntryActAction is set to any value
         other than 'forwardEsiL2' or 'forwardEsiL3'."
    DEFVAL { '00000000000000000000'H }
    ::= { tIPvXFltrEntryActionEntry 29 }

tIPvXFltrEntryActFwdEsiSvcId OBJECT-TYPE
    SYNTAX      TmnxServId
    MAX-ACCESS  read-create
    STATUS      current
    DESCRIPTION
        "The value of the object tIPvXFltrEntryActFwdEsiSvcId specifies
         the identifier of a VPLS used for VPN/DC connectivity.

         The value '0' indicates that there is no VPLS identifier specified.

         The non zero value of tIPvXFltrEntryActFwdEsiSvcId must be set
         together with a non zero value of tIPvXFltrEntryActEsi.

         Note that the value of tIPvXFltrEntryActFwdEsiSvcId is silently cleared
         by the system if the value of tIPvXFltrEntryActAction is set to any
         value other than 'forwardEsiL2'."
    DEFVAL { 0 }
    ::= { tIPvXFltrEntryActionEntry 30 }

tIPvXFltrEntryActFwdEsiVRtrId OBJECT-TYPE
    SYNTAX      TmnxVRtrIDOrZero
    MAX-ACCESS  read-create
    STATUS      current
    DESCRIPTION
       "The value of the object tIPvXFltrEntryActFwdEsiVRtrId specifies the
        VPRN/rVPLS virtual router identifier used for VPN/DC connectivity.

        The value '0' indicates that there is no VPRN/rVPLS virtual router
        identifier specified.

        The non zero value of tIPvXFltrEntryActFwdEsiVRtrId must be set
        together with non zero values of tIPvXFltrEntryActEsi,
        tIPvXFltrEntryActFwdEsiSFIpType and tIPvXFltrEntryActFwdEsiSFIp.

        Note that the value of tIPvXFltrEntryActFwdEsiVRtrId is silently cleared
        by the system if the value of tIPvXFltrEntryActAction is set to any
        value other than 'forwardEsiL3'."
    DEFVAL { 0 }
    ::= { tIPvXFltrEntryActionEntry 31 }

tIPvXFltrEntryActFwdEsiSFIpType OBJECT-TYPE
    SYNTAX      InetAddressType
    MAX-ACCESS  read-create
    STATUS      current
    DESCRIPTION
        "The value of the object tIPvXFltrEntryActFwdEsiSFIpType specifies the
         context in which the value of tIPvXFltrEntryActFwdEsiSFIp is
         interpreted.

         Only following values are supported:
            unknown(0)
            ipv4(1)
            ipv6(2)

         The value 'unknown' indicates that service function IP address type is
         not specified.

         If the value is different from 'unknown' it must be consistent with
         filter type given by the value of the object
         tIPvXFltrEntryActFltrType.

         The non zero value of tIPvXFltrEntryActFwdEsiSFIpType must be set
         together with a non zero values of tIPvXFltrEntryActFwdEsiSFIp,
         tIPvXFltrEntryActFwdEsiVRtrId and tIPvXFltrEntryActEsi.

         Note that the value of tIPvXFltrEntryActFwdEsiSFIpType is silently
         cleared by the system if the value of tIPvXFltrEntryActAction is set to
         any value other than 'forwardEsiL3'."
    DEFVAL { unknown }
    ::= { tIPvXFltrEntryActionEntry 32 }


tIPvXFltrEntryActFwdEsiSFIp OBJECT-TYPE
    SYNTAX      InetAddress (SIZE (0|4|16))
    MAX-ACCESS  read-create
    STATUS      current
    DESCRIPTION
        "The value of the object tIPvXFltrEntryActFwdEsiSFIp specifies the IP
         address of the service function toward which traffic is steered.

         The value '0' indicates that no service function IP address is
         specified.

         The non zero value of tIPvXFltrEntryActFwdEsiSFIp must be set together
         with a non zero values of tIPvXFltrEntryActFwdEsiSFIpType,
         tIPvXFltrEntryActFwdEsiVRtrId and tIPvXFltrEntryActEsi.

         Note that the value of tIPvXFltrEntryActFwdEsiSFIp is silently cleared
         by the system if the value of tIPvXFltrEntryActAction is set to any
         value other than 'forwardEsiL3'."
    DEFVAL { '00000000'H }
    ::= { tIPvXFltrEntryActionEntry 33 }

tIPvXFltrEntryActFwdEsiVasIf OBJECT-TYPE
    SYNTAX      InterfaceIndexOrZero
    MAX-ACCESS  read-create
    STATUS      current
    DESCRIPTION
       "The value of the object tIPvXFltrEntryActFwdEsiVasIf specifies the
        virtual router interface index of VPRN RVPLS interface used for VPN/DC
        connectivity.

        The value '0' indicates that no interface id is specified.

        The non zero value of tIPvXFltrEntryActFwdEsiVasIf must be set together
        with a non zero values of tIPvXFltrEntryActFwdEsiVRtrId,
        tIPvXFltrEntryActFwdEsiSFIp, tIPvXFltrEntryActFwdEsiSFIpType and
        tIPvXFltrEntryActEsi.

        Note: The value of tIPvXFltrEntryActFwdEsiVasIf is set to '0' by the
        system if the value of tIPvXFltrEntryActAction is set to any value
        other than 'forwardEsiL3'."
    DEFVAL { 0 }
    ::= { tIPvXFltrEntryActionEntry 34 }

tIPvXFltrEntryActRateLimit OBJECT-TYPE
    SYNTAX      TFilterEntryActionRateLimit
    UNITS       "kbps"
    MAX-ACCESS  read-create
    STATUS      current
    DESCRIPTION
        "The value of the object tIPvXFltrEntryActRateLimit specifies the
         rate to which the traffic matching the filter entry will be limited.

         The value of tIPvXFltrEntryActRateLimit can be set to non default value
         only if the value of tIPvXFltrEntryActAction is set to 'rateLimit'.

         Note that the value of tIPvXFltrEntryActRateLimit is silently cleared
         by the system if the value of tIPvXFltrEntryActAction is set to any
         value other than 'rateLimit'."
    DEFVAL { 0 }
    ::= { tIPvXFltrEntryActionEntry 35 }

tIPvXFltrEntryActPbrTargetStatus OBJECT-TYPE
    SYNTAX      TFilterPbrTargetStatus
    MAX-ACCESS  read-only
    STATUS      current
    DESCRIPTION
        "The value of the object tIPvXFltrEntryActPbrTargetStatus indicates the
         PBR target status.

         Refer to the description of the textual convention
         TFilterPbrTargetStatus for more information."
    ::= { tIPvXFltrEntryActionEntry 36 }

tIPvXFltrEntryActRemarkDSCP OBJECT-TYPE
    SYNTAX      TDSCPNameOrEmpty
    MAX-ACCESS  read-create
    STATUS      current
    DESCRIPTION
        "The value of the object tIPvXFltrEntryActRemarkDSCP specifies the
         value which remarks the DSCP value of packet matching the filter entry.

         The value of tIPvXFltrEntryActRemarkDSCP can be set to non default
         value only if the value of tIPvXFltrEntryActAction is set to
         'remarkDscp' or the value of tIPvXFltrEntryActActionExt is set to
         'remarkDscp' and the value of tIPvXFltrEntryActAction is set to one of
         the following values:

         forwardEsiL3
         forwardRtr
         forwardNextHop
         forwardNextHopRtr
         forwardNHInterface
         forwardLsp
         forwardRPlcy

         Note that the value of tIPvXFltrEntryActRemarkDSCP is silently cleared
         by the system if the value of tIPvXFltrEntryActAction is changed from
         'remarkDscp' to any other value or if tIPvXFltrEntryActActionExt is
         changed from 'remarkDscp' to any other value."
    DEFVAL { ''H }
    ::= { tIPvXFltrEntryActionEntry 37 }

tIPvXFltrEntryActActionExt OBJECT-TYPE
    SYNTAX      TIPvXFilterEntryActionExt
    MAX-ACCESS  read-create
    STATUS      current
    DESCRIPTION
        "The value of the object tIPvXFltrEntryActActionExt specifies the action
         to be taken on a packet along with action specified by
         tIPvXFltrEntryActAction.

         Refer to the description of the textual convention
         TIPvXFilterEntryActionExt for more information."
    DEFVAL { none }
    ::= { tIPvXFltrEntryActionEntry 38 }

tFltrEntryStatTable OBJECT-TYPE
    SYNTAX      SEQUENCE OF TFltrEntryStatEntry
    MAX-ACCESS  not-accessible
    STATUS      current
    DESCRIPTION
        "The table tFltrEntryStatTable contains statistics and counters
         pertaining to IPv4, IPv6 and MAC ACL filter entries."
   ::= { tFilterObjects 86 }

tFltrEntryStatEntry OBJECT-TYPE
    SYNTAX      TFltrEntryStatEntry
    MAX-ACCESS  not-accessible
    STATUS      current
    DESCRIPTION
        "The entry contains statistics pertaining to a particular
         IPv4, IPv6 or MAC ACL filter entry.

         Entries in this table are created by the system."
    INDEX { tFltrEntryStatFltrType,  tFltrEntryStatFltrId,
            tFltrEntryStatFltrEntryId }
    ::= { tFltrEntryStatTable 1 }

TFltrEntryStatEntry ::= SEQUENCE
    {
       tFltrEntryStatFltrType             TFilterType,
       tFltrEntryStatFltrId               TAnyFilterID,
       tFltrEntryStatFltrEntryId          TAnyEntryId,
       tFltrEntryStatIngHitCnt            Counter64,
       tFltrEntryStatIngHitCntB           Counter64,
       tFltrEntryStatEgrHitCnt            Counter64,
       tFltrEntryStatEgrHitCntB           Counter64,
       tFltrEntryStatRateLmtIngHitCnt     Counter64,
       tFltrEntryStatRateLmtIngHitCntB    Counter64,
       tFltrEntryStatRateLmtIngDrop       Counter64,
       tFltrEntryStatRateLmtIngDropB      Counter64,
       tFltrEntryStatRateLmtIngFwd        Counter64,
       tFltrEntryStatRateLmtIngFwdB       Counter64,
       tFltrEntryStatRateLmtEgrHitCnt     Counter64,
       tFltrEntryStatRateLmtEgrHitCntB    Counter64,
       tFltrEntryStatRateLmtEgrDrop       Counter64,
       tFltrEntryStatRateLmtEgrDropB      Counter64,
       tFltrEntryStatRateLmtEgrFwd        Counter64,
       tFltrEntryStatRateLmtEgrFwdB       Counter64
 }

tFltrEntryStatFltrType OBJECT-TYPE
    SYNTAX     TFilterType {
        fltrtypeselIp     (1),
        fltrtypeselMac    (2),
        fltrtypeselIpv6   (4)
    }
    MAX-ACCESS  not-accessible
    STATUS      current
    DESCRIPTION
        "The value of the object tFltrEntryStatFltrType specifies the type
         of ACL filter.

         Refer to the description of the textual convention TFilterType
         for more information."
    ::= { tFltrEntryStatEntry 1 }

tFltrEntryStatFltrId OBJECT-TYPE
    SYNTAX      TAnyFilterID
    MAX-ACCESS  not-accessible
    STATUS      current
    DESCRIPTION
        "The value of the object tFltrEntryStatFltrId specifies the filter
         id of an IP, IPv6 or MAC ACL filter based on the value of
         tFltrEntryStatFltrType.

         Refer to the description of the textual convention TAnyFilterID
         for more information."
    ::= { tFltrEntryStatEntry 2 }

tFltrEntryStatFltrEntryId OBJECT-TYPE
    SYNTAX      TAnyEntryId
    MAX-ACCESS  not-accessible
    STATUS      current
    DESCRIPTION
        "The value of the object tFltrEntryStatFltrEntryId specifies the entry
         id of filter of type IP, IPv6 or MAC based on the value of
         tFltrEntryStatFltrType.

         Refer to the description of the textual convention TAnyEntryId for more
         information."
    ::= { tFltrEntryStatEntry 3 }

tFltrEntryStatIngHitCnt OBJECT-TYPE
    SYNTAX      Counter64
    MAX-ACCESS  read-only
    STATUS      current
    DESCRIPTION
        "The value of the object tFltrEntryStatIngHitCnt indicates the
         number of times an ingress packet matched the filter entry."
    ::= { tFltrEntryStatEntry 4 }

tFltrEntryStatIngHitCntB OBJECT-TYPE
    SYNTAX      Counter64
    MAX-ACCESS  read-only
    STATUS      current
    DESCRIPTION
        "The value of tFltrEntryStatIngHitCntB indicates the number
         of bytes of all ingress packets that matched this entry."
    ::= { tFltrEntryStatEntry 5 }

tFltrEntryStatEgrHitCnt OBJECT-TYPE
    SYNTAX      Counter64
    MAX-ACCESS  read-only
    STATUS      current
    DESCRIPTION
        "The value of the object tFltrEntryStatEgrHitCnt indicates the
         number of times an egress packet matched the filter entry."
    ::= { tFltrEntryStatEntry 6 }

tFltrEntryStatEgrHitCntB OBJECT-TYPE
    SYNTAX      Counter64
    MAX-ACCESS  read-only
    STATUS      current
    DESCRIPTION
        "The value of tFltrEntryStatEgrHitCntB indicates the number
         of bytes of all egress packets that matched this entry."
    ::= { tFltrEntryStatEntry 7 }

tFltrEntryStatRateLmtIngHitCnt OBJECT-TYPE
    SYNTAX      Counter64
    MAX-ACCESS  read-only
    STATUS      current
    DESCRIPTION
        "The value of the object tFltrEntryStatRateLmtIngHitCnt indicates how
         many ingress packets were subjected to rate-limiting filter action."
    ::= { tFltrEntryStatEntry 8 }

tFltrEntryStatRateLmtIngHitCntB OBJECT-TYPE
    SYNTAX      Counter64
    MAX-ACCESS  read-only
    STATUS      current
    DESCRIPTION
        "The value of the object tFltrEntryStatRateLmtIngHitCntB indicates the
         number of bytes of all ingress packets that were subjected to
         rate-limiting filter action."
    ::= { tFltrEntryStatEntry 9 }

tFltrEntryStatRateLmtIngDrop OBJECT-TYPE
    SYNTAX      Counter64
    MAX-ACCESS  read-only
    STATUS      current
    DESCRIPTION
        "The value of the object tFltrEntryStatRateLmtIngDrop indicates how
         many ingress packets which were subjected to rate-limiting filter
         action were dropped."
    ::= { tFltrEntryStatEntry 10 }

tFltrEntryStatRateLmtIngDropB OBJECT-TYPE
    SYNTAX      Counter64
    MAX-ACCESS  read-only
    STATUS      current
    DESCRIPTION
        "The value of the object tFltrEntryStatRateLmtIngDropB indicates the
         number of bytes of all ingress packets which were subjected to
         rate-limiting filter action were dropped."
    ::= { tFltrEntryStatEntry 11 }

tFltrEntryStatRateLmtIngFwd OBJECT-TYPE
    SYNTAX      Counter64
    MAX-ACCESS  read-only
    STATUS      current
    DESCRIPTION
        "The value of the object tFltrEntryStatRateLmtIngFwd indicates how
         many ingress packets which were subjected to rate-limiting filter
         action were forwarded."
    ::= { tFltrEntryStatEntry 12 }

tFltrEntryStatRateLmtIngFwdB OBJECT-TYPE
    SYNTAX      Counter64
    MAX-ACCESS  read-only
    STATUS      current
    DESCRIPTION
        "The value of the object tFltrEntryStatRateLmtIngFwdB indicates the
         number of bytes of all ingress packets which were subjected to
         rate-limiting filter action were forwarded."
    ::= { tFltrEntryStatEntry 13 }

tFltrEntryStatRateLmtEgrHitCnt OBJECT-TYPE
    SYNTAX      Counter64
    MAX-ACCESS  read-only
    STATUS      current
    DESCRIPTION
        "The value of the object tFltrEntryStatRateLmtEgrHitCnt indicates how
         many egress packets were subjected to rate-limiting filter action."
    ::= { tFltrEntryStatEntry 14 }

tFltrEntryStatRateLmtEgrHitCntB OBJECT-TYPE
    SYNTAX      Counter64
    MAX-ACCESS  read-only
    STATUS      current
    DESCRIPTION
        "The value of the object tFltrEntryStatRateLmtEgrHitCntB indicates the
         number of bytes of all egress packets that were subjected to
         rate-limiting filter action."
    ::= { tFltrEntryStatEntry 15 }

tFltrEntryStatRateLmtEgrDrop OBJECT-TYPE
    SYNTAX      Counter64
    MAX-ACCESS  read-only
    STATUS      current
    DESCRIPTION
        "The value of the object tFltrEntryStatRateLmtEgrDrop indicates how
         many egress packets which were subjected to rate-limiting filter
         action were dropped."
    ::= { tFltrEntryStatEntry 16 }

tFltrEntryStatRateLmtEgrDropB OBJECT-TYPE
    SYNTAX      Counter64
    MAX-ACCESS  read-only
    STATUS      current
    DESCRIPTION
        "The value of the object tFltrEntryStatRateLmtEgrDropB indicates the
         number of bytes of all egress packets which were subjected to
         rate-limiting filter action were dropped."
    ::= { tFltrEntryStatEntry 17 }

tFltrEntryStatRateLmtEgrFwd OBJECT-TYPE
    SYNTAX      Counter64
    MAX-ACCESS  read-only
    STATUS      current
    DESCRIPTION
        "The value of the object tFltrEntryStatRateLmtEgrFwd indicates how
         many egress packets which were subjected to rate-limiting filter
         action were forwarded."
    ::= { tFltrEntryStatEntry 18 }

tFltrEntryStatRateLmtEgrFwdB OBJECT-TYPE
    SYNTAX      Counter64
    MAX-ACCESS  read-only
    STATUS      current
    DESCRIPTION
        "The value of the object tFltrEntryStatRateLmtEgrFwdB indicates the
         number of bytes of all egress packets which were subjected to
         rate-limiting filter action were forwarded."
    ::= { tFltrEntryStatEntry 19 }

-- ----------------------------
--  tFltrPrefListInfoTable
-- ----------------------------

tFltrPrefListInfoTable OBJECT-TYPE
    SYNTAX      SEQUENCE OF TFltrPrefListInfoEntry
    MAX-ACCESS  not-accessible
    STATUS      current
    DESCRIPTION
        "The table tFltrPrefListInfoTable contains all prefixes from all prefix
         lists. Both implicitly or explicitly defined."
    ::= { tFilterObjects 87 }

tFltrPrefListInfoEntry OBJECT-TYPE
    SYNTAX      TFltrPrefListInfoEntry
    MAX-ACCESS  not-accessible
    STATUS      current
    DESCRIPTION
        "An entry in the tFltrPrefListInfoTable contains information pertaining
         to a particular IP address prefix which is part of filter prefix list."
    INDEX {tFilterPrefixListType,
           tFilterPrefixListName,
           tFltrPrefListInfoPrefixSrc,
           tFltrPrefListInfoPrefixSrcIndex,
           tFltrPrefListInfoPrefixType,
           tFltrPrefListInfoPrefix,
           tFltrPrefListInfoPrefixLen
           }
    ::= { tFltrPrefListInfoTable 1 }

TFltrPrefListInfoEntry ::=
    SEQUENCE {
        tFltrPrefListInfoPrefixSrc      INTEGER,
        tFltrPrefListInfoPrefixSrcIndex Unsigned32,
        tFltrPrefListInfoPrefixType     InetAddressType,
        tFltrPrefListInfoPrefix         InetAddress,
        tFltrPrefListInfoPrefixLen      InetAddressPrefixLength,
        tFltrPrefListInfoPrefixOwner    INTEGER
    }

tFltrPrefListInfoPrefixSrc OBJECT-TYPE
    SYNTAX INTEGER {
        prefixConfig       (0),
        applyPathBgpPeer   (1)
    }
    MAX-ACCESS  not-accessible
    STATUS      current
    DESCRIPTION
        "The value of the object tFltrPrefListInfoPrefixSrc indicates the source
         of the prefix. If the value is different from 'prefixConfig' then the
         value corresponds to tFilterApplyPathSource value."
    ::= { tFltrPrefListInfoEntry 1 }

tFltrPrefListInfoPrefixSrcIndex OBJECT-TYPE
    SYNTAX      Unsigned32
    MAX-ACCESS  not-accessible
    STATUS      current
    DESCRIPTION
        "The value of the object tFltrPrefListInfoPrefixSrcIndex indicates the
         index of the apply-path rule which is the source of the prefix. If the
         value of tFltrPrefListInfoPrefixSrcIndex is '0', then there is no
         corresponding apply-path rule. In such case the value of
         tFltrPrefListInfoPrefixSrc is 'prefixConfig'."
    ::= { tFltrPrefListInfoEntry 2 }

tFltrPrefListInfoPrefixType OBJECT-TYPE
    SYNTAX      InetAddressType
    MAX-ACCESS  not-accessible
    STATUS      current
    DESCRIPTION
        "The value of the object tFltrPrefListInfoPrefixType indicates whether
         the prefix is an IPv4 or IPv6 prefix."
    ::= { tFltrPrefListInfoEntry 3 }

tFltrPrefListInfoPrefix OBJECT-TYPE
    SYNTAX      InetAddress (SIZE (4|16))
    MAX-ACCESS  not-accessible
    STATUS      current
    DESCRIPTION
        "The value of the object tFltrPrefListInfoPrefix indicates the IP
         prefix."
    ::= { tFltrPrefListInfoEntry 4 }

tFltrPrefListInfoPrefixLen OBJECT-TYPE
    SYNTAX      InetAddressPrefixLength
    MAX-ACCESS  not-accessible
    STATUS      current
    DESCRIPTION
        "The value of the object tFltrPrefListInfoPrefixLen indicates
         the IP prefix length."
    ::= { tFltrPrefListInfoEntry 5 }


tFltrPrefListInfoPrefixOwner OBJECT-TYPE
    SYNTAX      INTEGER {
        config      (0),
        applyPath   (1)
    }
    MAX-ACCESS  read-only
    STATUS      current
    DESCRIPTION
        "The value of the object tFltrPrefListInfoPrefixOwner indicates whether
         the prefix was inserted into the prefix list implicitly by an apply
         path rule or explicitly by a prefix configuration."
    ::= { tFltrPrefListInfoEntry 6 }

--
--
-- Filter Notification Objects
--

tFilterPBRDropReason OBJECT-TYPE
    SYNTAX      INTEGER {
                invalidInterface (0),
                interfaceDown    (1)
            }
    MAX-ACCESS  accessible-for-notify
    STATUS      current
    DESCRIPTION
        "Used by tIPFilterPBRPacketsDrop to report the failure reason code."
    ::= { tFilterNotificationObjects 1 }

tFilterParmRow OBJECT-TYPE
    SYNTAX      RowPointer
    MAX-ACCESS  accessible-for-notify
    STATUS      current
    DESCRIPTION
        "The value of the object tFilterParmRow indicates the OID of the row
         status of the applicable filter parameter table. This can be a row from
         either one of the following tables:
         - tIPFilterParamsTable;
         - tMacFilterParamsTable; or
         - tIPv6FilterParamsTable"
    ::= { tFilterNotificationObjects 2 }

tFilterAlarmDescription OBJECT-TYPE
    SYNTAX      DisplayString
    MAX-ACCESS  accessible-for-notify
    STATUS      current
    DESCRIPTION
        "The value of the object tFilterAlarmDescription is a printable
         character string which contains information about the cause of the
         problem."
    ::= { tFilterNotificationObjects 3 }

tFilterId OBJECT-TYPE
    SYNTAX      TFilterID
    MAX-ACCESS  accessible-for-notify
    STATUS      current
    DESCRIPTION
        "The value of the object tFilterId, together with the object
         tFilterType uniquely defines the filter for which this notification is
         generated."
    ::= { tFilterNotificationObjects 4 }

tFilterType OBJECT-TYPE
    SYNTAX      TFilterType
    MAX-ACCESS  accessible-for-notify
    STATUS      current
    DESCRIPTION
        "The value of the object tFilterType, together with the object
         tFilterId uniquely defines the filter for which this notification is
         generated."
    ::= { tFilterNotificationObjects 5 }

tFilterSubInsSpaceOwner OBJECT-TYPE
    SYNTAX      TFilterSubInsSpaceOwner
    MAX-ACCESS  accessible-for-notify
    STATUS      current
    DESCRIPTION
        "The value of the object tFilterSubInsSpaceOwner, specifies for
         which application, capable of inserting filter entries,
         this notification is generated."
    ::= { tFilterNotificationObjects 6 }

tFilterThresholdReached OBJECT-TYPE
    SYNTAX      INTEGER
    MAX-ACCESS  accessible-for-notify
    STATUS      current
    DESCRIPTION
        "The value of the object tFilterThresholdReached, specifies
         the threshold reached at the moment this notification was
         generated."
    ::= { tFilterNotificationObjects 7 }

tFltrFlowSpecProblem OBJECT-TYPE
    SYNTAX      INTEGER {
                nlriDecodeProblem           (0),
                maxNbrFlowSpecEntriesReached(1),
                fltrResourceProblem         (2),
                other                       (3)}
    MAX-ACCESS  accessible-for-notify
    STATUS      current
    DESCRIPTION
        "The value of the object tFltrFlowSpecProblem, indicates
         which problem has occurred while processing a BGP flowspec
         NLRI in the filter module."
    ::= { tFilterNotificationObjects 8 }

tFltrFlowSpecProblemDescription OBJECT-TYPE
    SYNTAX      DisplayString
    MAX-ACCESS  accessible-for-notify
    STATUS      current
     DESCRIPTION
         "The value of the object tFltrFlowSpecProblemDescription may contain
          a more detailed problem description then as given by
          tFltrFlowSpecProblem."
    ::= { tFilterNotificationObjects 9 }

tFltrFLowSpecNLRI OBJECT-TYPE
    SYNTAX      OCTET STRING
    MAX-ACCESS  accessible-for-notify
    STATUS      current
    DESCRIPTION
        "The value of the object tFltrFLowSpecNLRI contains
         at most the first 30 octets of the NLRI causing the problem."
    ::= { tFilterNotificationObjects 10 }

tFltrFlowSpecVrtrId OBJECT-TYPE
    SYNTAX      Unsigned32
    MAX-ACCESS  accessible-for-notify
    STATUS      current
     DESCRIPTION
         "The value of the object tFltrFlowSpecVrtrId indicates
          the virtual router Id to which the NLRI belongs."
    ::= { tFilterNotificationObjects 11 }
    
tFltrPrefixListType OBJECT-TYPE
    SYNTAX      TFltrPrefixListType
    MAX-ACCESS  accessible-for-notify
    STATUS      current
    DESCRIPTION
         "The value of the object tFltrPrefixListType indicates
          the type of prefix-list."
    ::= { tFilterNotificationObjects 12 }
    
tFltrPrefixListName OBJECT-TYPE
    SYNTAX      TNamedItem
    MAX-ACCESS  accessible-for-notify
    STATUS      current
    DESCRIPTION
         "The value of the object tFltrPrefixListName indicates
          the name of the prefix-list."
    ::= { tFilterNotificationObjects 13 }    
    
tFltrApplyPathSource OBJECT-TYPE
    SYNTAX      TmnxFilterApplyPathSource
    MAX-ACCESS  accessible-for-notify
    STATUS      current
    DESCRIPTION
        "The value of tFltrApplyPathSource indicates the source of the
         apply-path rule."
    ::= { tFilterNotificationObjects 14 }    

tFltrApplyPathIndex OBJECT-TYPE
    SYNTAX      Unsigned32
    MAX-ACCESS  accessible-for-notify
    STATUS      current
    DESCRIPTION
        "The value of tFltrApplyPathIndex indicates the index of the
         apply-path rule."
    ::= { tFilterNotificationObjects 15 } 
    
tFltrNotifDescription OBJECT-TYPE
    SYNTAX      DisplayString
    MAX-ACCESS  accessible-for-notify
    STATUS      current
     DESCRIPTION
         "The value of the object tFltrNotifDescription may contain
          a description text."
    ::= { tFilterNotificationObjects 16 }   

tFltrMdaId OBJECT-TYPE
    SYNTAX      TmnxPortID
    MAX-ACCESS  accessible-for-notify
    STATUS      current
     DESCRIPTION
         "The value of the object tFltrMdaId contains the MDA-id
          of the mda on which an filter event is being reported."
    ::= { tFilterNotificationObjects 17 }   

tIPFilterPBRPacketsDrop NOTIFICATION-TYPE
    OBJECTS {
        tIPFilterParamsForwardNHInterface,
        tFilterPBRDropReason
    }
    STATUS      current
    DESCRIPTION
        "The tIPFilterPBRPacketsDrop event is generated either
         when the configuration of a forwarding action refers to an
         invalid/unconfigured next-hop or if the active interface goes down
         operationally in the process of active filtering."
    ::= { tFilterNotifications 1 }

tFilterEntryActivationFailed NOTIFICATION-TYPE
    OBJECTS {
        tFilterParmRow,
        tFilterAlarmDescription
    }
    STATUS      obsolete
    DESCRIPTION
        "The tFilterEntryActivationFailed event can only be
         generated for entries that are controlled by a tmnxTimeRangeEntry.
         If the tmnxTimeRangeEntry becomes active the indicated entry must be
         installed.
         The event is generated when this installation failed because
         of resource problems.

         This object is obsoleted in release 14.0."
    ::= { tFilterNotifications 2 }

tFilterEntryActivationRestored NOTIFICATION-TYPE
    OBJECTS {
        tFilterParmRow,
        tFilterAlarmDescription
    }
    STATUS      obsolete
    DESCRIPTION
        "The tFilterEntryActivationRestored event can only be
         generated for entries that are controlled by a tmnxTimeRangeEntry.
         If the tmnxTimeRangeEntry becomes active the indicated entry must be
         installed.
         The event tFilterEntryActivationFailed is generated when
         this installation originally failed because of resources
         problems,
         The notification tFilterEntryActivationRestored is sent
         when either the time range associated with the filter is no
         longer active, or when the filter entry
         was installed due to the availability of new resources.

         This object is obsoleted in release 14.0."
    ::= { tFilterNotifications 3 }

tFilterSubInsSpaceAlarmRaised NOTIFICATION-TYPE
    OBJECTS {
        tFilterType,
        tFilterId,
        tFilterSubInsSpaceOwner,
        tFilterThresholdReached
    }
    STATUS      current
    DESCRIPTION
        "The tFilterSubInsSpaceAlarmRaised notification is
         generated when the utilization of a filter entry
         range that was reserved for filter entry insertion
         increases to the configured high watermark for his filter"
    ::= { tFilterNotifications 4 }

tFilterSubInsSpaceAlarmCleared NOTIFICATION-TYPE
    OBJECTS {
        tFilterType,
        tFilterId,
        tFilterSubInsSpaceOwner,
        tFilterThresholdReached
    }
    STATUS      current
    DESCRIPTION
        "The tFilterSubInsSpaceAlarmCleared notification is
         generated when the utilization of a filter entry
         range that was reserved for filter entry insertion
         dropped below to the configured low watermark for his filter."
    ::= { tFilterNotifications 5 }

tFilterSubInsFltrEntryDropped NOTIFICATION-TYPE
    OBJECTS {
        tFilterType,
        tFilterId,
        tFilterSubInsSpaceOwner,
        tFilterAlarmDescription
    }
    STATUS      current
    DESCRIPTION
        "The tFilterSubInsFltrEntryDropped notification is
         generated when a request to insert a filter entry
         was not successful."
    ::= { tFilterNotifications 6 }

tFilterBgpFlowSpecProblem NOTIFICATION-TYPE
    OBJECTS {
        tFilterType,
        tFltrFlowSpecVrtrId,
        tFltrFlowSpecProblem,
        tFltrFlowSpecProblemDescription,
        tFltrFLowSpecNLRI
    }
    STATUS      current
    DESCRIPTION
        "The tFilterBgpFlowSpecProblem notification is
         generated when a BGP flowspec NLRI is received in
         the filter module that cannot be treated - i.e. for
         which no filter entry is installed in the system,
         or when there is a problem inserting (new) or
         reshuffling (existing) flowspec or merged filter entries."
    ::= { tFilterNotifications 7 }

tFilterApplyPathProblem NOTIFICATION-TYPE
    OBJECTS {
        tFltrPrefixListType,
        tFltrPrefixListName,
        tFltrApplyPathSource,
        tFltrApplyPathIndex,
        tFilterAlarmDescription
    }
    STATUS     current
    DESCRIPTION
        "The tFilterApplyPathProblem notification is generated when 
         when a problem is encountered for a configured apply-path rule."
    ::= { tFilterNotifications 8 }

tFilterRadSharedFltrAlarmRaised  NOTIFICATION-TYPE
    OBJECTS {
        tFilterType,
        tFilterId,
        tFilterThresholdReached
    }
    STATUS      current
    DESCRIPTION
        "The tFilterRadSharedFltrAlarmRaised notification is
         generated when the number of Radius Shared Filters that are
         dynamically created in the system increases to the
         configured high watermark for the indicated filter."
    ::= { tFilterNotifications 9 }

tFilterRadSharedFltrAlarmClear   NOTIFICATION-TYPE
    OBJECTS {
        tFilterType,
        tFilterId,
        tFilterThresholdReached
    }
    STATUS      current
    DESCRIPTION
        "The tFilterRadSharedFltrAlarmClear notification is generated
         when the number of Radius Shared Filters that are
         dynamically created in the system dropped below to the
         configured low watermark for the indicated filter."
    ::= { tFilterNotifications 10 }

tFilterEmbeddingOperStateChange   NOTIFICATION-TYPE
    OBJECTS {
        tFilterEmbeddedRefOperState,
        tFltrNotifDescription
    }
    STATUS      current
    DESCRIPTION
        "The tFilterEmbeddingOperStateChange notification is generated
         when the operational status of an embedded filter has changed.
         
         [CAUSE] This notification may be triggered for the following reasons:
         
         1) An attempt to embed an embedded filter into embedding filter was done.
         2) An attempt to recover an embedding that is operationally down 
            was done.
         3) An attempt to change the admin state of an embedding was done.
         4) The operational state of an embedding has changed to inactive 
            due to lack of resources.
            
         [EFFECT] The effect depends on the new state. If the new state is 'active',
         the embedding of the filter was successful. 
         
         If the new state is 'embedFailedNoResources' the embedding was not successful 
         due to lack of resources.

         If the new state is 'inactive' and the previous state was 'active' then 
         the embedded entries were removed. Otherwise the embedding filter was 
         not changed.
         
         [RECOVERY] If the new state is 'active' or 'inactive', no action is required. 
         
         If the new state is 'embedFailedNoResources', an attempt to recover the operational 
         state can be done by removal and reapplication of the embedding."
    ::= { tFilterNotifications 11 }

tFilterEmbedOpenflowOperStateChg   NOTIFICATION-TYPE
    OBJECTS {
        tFilterEmbedOpenflowOperState,
        tFltrNotifDescription
    }
    STATUS      current
    DESCRIPTION
        "The tFilterEmbedOpenflowOperStateChg notification is generated
         when the operational state of an open-flow switch embedded 
         in a filter with scope other than 'embedded' has changed.
         
         [CAUSE] This notification may be triggered for the following reasons:
         
         1) An attempt to embed an open-flow switch into an embedding filter 
            was done.
         2) An attempt to recover an open-flow embedding that is operationally 
            down was done.
         3) An attempt to change the admin state of an open-flow embedding 
            was done.
         4) The operational state of an open-flow embedding has changed 
            to inactive due to lack of resources.
            
         [EFFECT] The effect depends on the new state. If the new state 
         is 'active', the embedding of an open-flow switch was successful. 
         
         If the new state is 'embedFailedNoResources' the embedding was not 
         successful due to lack of resources.

         If the new state is 'inactive' and the previous state was 'active' then 
         the open-flow switch entries were removed. 
         Otherwise the embedding filter was not changed.
         
         [RECOVERY] If the new state is 'active' or 'inactive', no action 
         is required. 
         
         If the new state is 'embedFailedNoResources', an attempt to recover 
         the operational state can be done by removal and reapplication of 
         the open-flow embedding."
    ::= { tFilterNotifications 12 }

tFilterTmsEvent  NOTIFICATION-TYPE
    OBJECTS {
        tFltrMdaId,
        tFltrNotifDescription
    }
    STATUS      current
    DESCRIPTION
        "The tFilterTmsEvent notification is generated by the systems filter
         module to report an event related to the
         Threat Management System (TMS).
         
         Receiving the tFilterTmsEvent notification is an indication that
         the TMS system may not be fully operational."
    ::= { tFilterNotifications 13 }

tFilterEmbedFlowspecOperStateChg   NOTIFICATION-TYPE
    OBJECTS {
        tFilterEmbedFlowspecRtrId,
        tFilterEmbedFlowspecOperState,
        tFltrNotifDescription
    }
    STATUS      current
    DESCRIPTION
        "The tFilterEmbedFlowspecOperStateChg notification is generated
         when the operational state of a set of flowspec rules embedded in
         an IP or IPv6 filter with scope other than 'embedded' has changed.

         [CAUSE] This notification may be triggered for the following reasons:

         1) An attempt to embed a set of flowspec rules into an embedding
            filter was done.
         2) An attempt to recover a flowspec rules embedding that is
            operationally down was done.
         3) An attempt to change the admin state of a flowspec rules embedding
            was done.
         4) The operational state of a flowspec rules embedding has changed
            to inactive due to lack of resources.

         [EFFECT] The effect depends on the new state. If the new state
         is 'active', the embedding of a set of flowspec rules was successful.

         If the new state is 'embedFailedNoResources' the embedding was not
         successful due to lack of resources.

         If the new state is 'inactive' and the previous state was 'active' then
         the set of flowspec rules were removed.

         Otherwise the embedding filter was not changed.

         [RECOVERY] If the new state is 'active' or 'inactive', no action
         is required.

         If the new state is 'embedFailedNoResources', an attempt to recover
         the operational state can be done by removal and reapplication of
         the flowspec rules embedding."
    ::= { tFilterNotifications 14 }

tFilterEmbedVsdOperStateChg   NOTIFICATION-TYPE
    OBJECTS {
        tFilterEmbedVsdOperState,
        tFltrNotifDescription
    }
    STATUS      current
    DESCRIPTION
        "The tFilterEmbedVsdOperStateChg notification is generated
         when the operational state of an embedding of a filter managed
         by a VSD controller in a filter with scope other than 'embedded'
         has changed.

         [CAUSE] This notification may be triggered for the following reasons:

         1) An attempt to embed a filter managed by a VSD controller
            into an embedding filter was done.
         2) An attempt to recover an embedding that is operationally down
            was done.
         3) An attempt to change the admin state of an embedding was done.
         4) The operational state of an embedding has changed to inactive 
            due to lack of resources.

         [EFFECT] The effect depends on the new state. If the new state
         is 'active', the embedding of a filter managed by a VSD controller
         was successful.

         If the new state is 'embedFailedNoResources' the embedding was not
         successful due to lack of resources.

         If the new state is 'inactive' and the previous state was 'active'
         then the embedded entries were removed.

         Otherwise the embedding filter was not changed.

         [RECOVERY] If the new state is 'active' or 'inactive', no action
         is required.

         If the new state is 'embedFailedNoResources', an attempt to recover
         the operational state can be done by removal and reapplication
         of the embedding."
    ::= { tFilterNotifications 15 }

--
-- Conformance Information
--

tFilterMIBCompliances OBJECT IDENTIFIER ::= { tFilterMIBConformance 1 }
tFilterMIBGroups      OBJECT IDENTIFIER ::= { tFilterMIBConformance 2 }

--
-- Compliance Statements
--

-- tFilterMIBCompliance MODULE-COMPLIANCE
--    ::= { tFilterMIBCompliances 1 }

-- tFilterR2r1MIBCompliance MODULE-COMPLIANCE
--    ::= { tFilterMIBCompliances 2 }

-- tFilterV3v0MIBCompliance MODULE-COMPLIANCE
--    ::= { tFilterMIBCompliances 3 }

tFilter7450V4v0Compliance MODULE-COMPLIANCE
    STATUS  obsolete
    DESCRIPTION
        "The compliance statement for management of Filter features
         on Nokia 7450 ESS series systems release R4.0."
    MODULE  -- this module
        MANDATORY-GROUPS {
            tFilterScalarGroup,
            tIPFilterV4v0Group,
            tMacFilterV4v0Group,
            tFilterLogGroup,
            tFilterRedirectPolicyGroup,
            tFilterNotificationsGroup
            -- tIPv6FilterV4v0Group
            -- tTodPoliciesV4v0Group
        }
    ::= { tFilterMIBCompliances 4 }

tFilter7750V4v0Compliance MODULE-COMPLIANCE
    STATUS  obsolete
    DESCRIPTION
        "The compliance statement for management of Filter features
         on Nokia 7750 SR series systems release R4.0."
    MODULE  -- this module
        MANDATORY-GROUPS {
            tFilterScalarGroup,
            tIPFilterV4v0Group,
            tMacFilterV4v0Group,
            tFilterLogGroup,
            tFilterRedirectPolicyGroup,
            tFilterNotificationsGroup,
            tIPv6FilterV4v0Group
            -- tTodPoliciesV4v0Group
        }
    ::= { tFilterMIBCompliances 5 }

tFilter7450V5v0Compliance MODULE-COMPLIANCE
    STATUS  obsolete
    DESCRIPTION
        "The compliance statement for management of Filter features
         on Nokia 7450 ESS series systems release R5.0."
    MODULE  -- this module
        MANDATORY-GROUPS {
            tFilterScalarGroup,
            tIPFilterV5v0Group,
            tMacFilterV4v0Group,
            tFilterLogGroup,
            tFilterRedirectPolicyGroup,
            tFilterNotificationsGroup,
            -- tIPv6FilterV4v0Group
            tTodPolicies77450V5v0Group,
            tToDPoliciesV5v0NotifyGroup,
            tFilterLogV5v0Group
        }
    ::= { tFilterMIBCompliances 6 }

tFilter77x0V5v0Compliance MODULE-COMPLIANCE
    STATUS  obsolete
    DESCRIPTION
        "The compliance statement for management of Filter features
         on Nokia 77x0 SPR/SR series systems release R5.0."
    MODULE  -- this module
        MANDATORY-GROUPS {
            tFilterScalarGroup,
            tIPFilterV5v0Group,
            tMacFilterV4v0Group,
            tFilterLogGroup,
            tFilterRedirectPolicyGroup,
            tFilterNotificationsGroup,
            tIPv6FilterV4v0Group,
            tTodPolicies77x0V5v0Group,
            tToDPoliciesV5v0NotifyGroup,
            tFilterLogV5v0Group
        }
    ::= { tFilterMIBCompliances 7 }

tFilter7450V6v0Compliance MODULE-COMPLIANCE
    STATUS  obsolete
    DESCRIPTION
        "The compliance statement for management of Filter features
         on Nokia 7450 ESS series systems release R5.0."
    MODULE  -- this module
        MANDATORY-GROUPS {
            tFilterScalarGroup,
            tIPFilterV6v0Group,
            tMacFilterV6v0Group,
            tFilterLogGroup,
            tFilterRedirectPolicyGroup,
            tFilterNotificationsGroup,
            -- tIPv6FilterV6v0Group
            tTodPolicies77450V5v0Group,
            tToDPoliciesV5v0NotifyGroup,
            tFilterLogV5v0Group
        }
    ::= { tFilterMIBCompliances 8 }

tFilter77x0V6v0Compliance MODULE-COMPLIANCE
    STATUS  obsolete
    DESCRIPTION
        "The compliance statement for management of Filter features
         on Nokia 77x0 SPR/SR series systems release R5.0."
    MODULE  -- this module
        MANDATORY-GROUPS {
            tFilterScalarGroup,
            tIPFilterV6v0Group,
            tMacFilterV6v0Group,
            tFilterLogGroup,
            tFilterRedirectPolicyGroup,
            tFilterNotificationsGroup,
            tIPv6FilterV6v0Group,
            tTodPolicies77x0V5v0Group,
            tToDPoliciesV5v0NotifyGroup,
            tFilterLogV5v0Group
        }
    ::= { tFilterMIBCompliances 9 }

tFilter7450V8v0Compliance MODULE-COMPLIANCE
    STATUS  obsolete
    DESCRIPTION
        "The compliance statement for management of Filter features
         on Nokia 7450 ESS series systems release R8.0."
    MODULE  -- this module
        MANDATORY-GROUPS {
            tFilterScalarGroup,
            tIPFilterV8v0Group,
            tFilterLogGroup,
            tFilterLogV5v0Group,
            tFilterRedirectPolicyGroup,
            tFilterNotificationsV8v0Group,
            tFilterNotificationObjV8v0Group,
            -- tIPv6FilterV8v0Group
            tTodPolicies77450V5v0Group,
            -- tTodPolicies77x0V5v0Group,
            tToDPoliciesV5v0NotifyGroup
        }
    ::= { tFilterMIBCompliances 10 }

tFilter77x0V8v0Compliance MODULE-COMPLIANCE
    STATUS  obsolete
    DESCRIPTION
        "The compliance statement for management of Filter features
         on Nokia 77x0 SPR/SR series systems release R8.0."
    MODULE  -- this module
        MANDATORY-GROUPS {
            tFilterScalarGroup,
            tIPFilterV8v0Group,
            tMacFilterV8v0Group,
            tFilterLogGroup,
            tFilterLogV5v0Group,
            tFilterRedirectPolicyGroup,
            tFilterNotificationsV8v0Group,
            tFilterNotificationObjV8v0Group,
            tIPv6FilterV8v0Group,
            -- tTodPolicies77450V5v0Group,
            tTodPolicies77x0V5v0Group,
            tToDPoliciesV5v0NotifyGroup
        }
    ::= { tFilterMIBCompliances 11 }

tFilter7xxxV9v0Compliance MODULE-COMPLIANCE
    STATUS  obsolete
    DESCRIPTION
        "The compliance statement for management of Filter features
         on Nokia 77x0 SPR/SR series systems release R9.0."
    MODULE  -- this module
        MANDATORY-GROUPS {
            tFilterScalarGroup,
            tIPFilterV9v0Group,
            tMacFilterV8v0Group,
            tFilterLogGroup,
            tFilterLogV5v0Group,
            tFilterRedirectPolicyGroup,
            tFilterNotificationsV9v0Group,
            tFilterNotificationObjV9v0Group,
            tIPv6FilterV8v0Group,
            tTodPolicies77x0V5v0Group,
            tToDPoliciesV5v0NotifyGroup,
            tMacFilterVidFilteringV9v0Group,
            tDhcpFilterV9v0Group
        }
    ::= { tFilterMIBCompliances 12 }

tFilter7xxxV10v0Compliance MODULE-COMPLIANCE
    STATUS  obsolete
    DESCRIPTION
        "The compliance statement for management of Filter features
         on Nokia 77x0 SPR/SR series systems release R10.0."
    MODULE  -- this module
        MANDATORY-GROUPS {
            tFilterScalarGroup,
            tIPFilterV9v0Group,
            tMacFilterV8v0Group,
            tFilterLogGroup,
            tFilterLogV5v0Group,
            tFilterRedirectPolicyGroup,
            tFilterNotificationsV9v0Group,
            tFilterNotificationObjV9v0Group,
            tIPv6FilterV10v0Group,
            tTodPolicies77x0V5v0Group,
            tToDPoliciesV5v0NotifyGroup,
            tMacFilterVidFilteringV9v0Group,
            tDhcpFilterV10v0Group,
            tFilterNameV10v0Group,
            tLiFilterV10v0Group,
            tFilterPrefixListV10v0Group
        }
    ::= { tFilterMIBCompliances 13 }

tFilter7xxxV11v0Compliance MODULE-COMPLIANCE
    STATUS obsolete
    DESCRIPTION
        "The compliance statement for management of Filter features
         on Nokia 77x0 SPR/SR series systems release R11.0."
    MODULE  -- this module
        MANDATORY-GROUPS {
            tFilterScalarGroup,
            tIPFilterV11v0Group,
            tMacFilterV8v0Group,
            tFilterLogGroup,
            tFilterLogV5v0Group,
            tFilterRedirectPolicyGroup,
            tFilterNotificationsV11v0Group,
            tFilterNotificationObjV11v0Group,
            tIPv6FilterV11v0Group,
            tTodPolicies77x0V5v0Group,
            tToDPoliciesV5v0NotifyGroup,
            tMacFilterVidFilteringV9v0Group,
            tDhcpFilterV10v0Group,
            tFilterNameV10v0Group,
            tLiFilterV10v0Group,
            tFilterPrefixListV11v0Group,
            tFilterEmbeddedInsertV11v0Group,
            tFilterPortListV11v0Group
        }
    ::= { tFilterMIBCompliances 14 }

tFilter7xxxV12v0Compliance MODULE-COMPLIANCE
    STATUS  obsolete
    DESCRIPTION
        "The compliance statement for management of Filter features
         on Nokia 77x0 SPR/SR series systems release R12.0."
    MODULE  -- this module
        MANDATORY-GROUPS {
            tFilterScalarGroup,
            tIPFilterV12v0Group,
            tMacFilterV8v0Group,
            tFilterLogGroup,
            tFilterLogV5v0Group,
            tFilterRedirectPolicyGroup,
            tFilterNotificationsV11v0Group,
            tFilterNotificationsV12v0Group,
            tFilterNotificationObjV12v0Group,
            tIPv6FilterV12v0Group,
            tTodPolicies77x0V5v0Group,
            tToDPoliciesV5v0NotifyGroup,
            tMacFilterVidFilteringV9v0Group,
            tDhcpFilterV10v0Group,
            tFilterNameV10v0Group,
            tLiFilterV12v0Group,
            tFilterPrefixListV11v0Group,
            tFilterEmbeddedInsertV11v0Group,
            tFilterEmbeddedInsertV12v0Group,
            tFilterPortListV11v0Group
        }
    ::= { tFilterMIBCompliances 15 }

tFilterV13v0Compliance MODULE-COMPLIANCE
    STATUS  obsolete
    DESCRIPTION
        "The compliance statement for management of Filter features
         on Nokia 77x0 SPR/SR series systems release R13.0."
    MODULE  -- this module
        MANDATORY-GROUPS {
            tFilterScalarGroup,
            tIPFilterV12v0Group,
            tIPFilterV13v0Group,
            tMacFilterV8v0Group,
            tFilterLogGroup,
            tFilterLogV5v0Group,
            tFilterRedirectPolicyV13v0Group,
            tFilterNotificationsV11v0Group,
            tFilterNotificationsV12v0Group,
            tFilterNotificationObjV12v0Group,
            tIPv6FilterV12v0Group,
            tIPv6FilterV13v0Group,
            tTodPolicies77x0V5v0Group,
            tToDPoliciesV5v0NotifyGroup,
            tMacFilterVidFilteringV9v0Group,
            tDhcpFilterV10v0Group,
            tDhcpFilterV13v0Group,
            tFilterNameV10v0Group,
            tLiFilterV12v0Group,
            tFilterPrefixListV11v0Group,
            tFilterEmbeddedInsertV11v0Group,
            tFilterEmbeddedInsertV12v0Group,
            tFilterEmbeddedInsertV13v0Group,
            tFilterPortListV11v0Group,
            tFilterSystemFilterV13v0Group,
            tMacFilterV13v0Group
        }
    ::= { tFilterMIBCompliances 16 }

tFilterV14v0Compliance MODULE-COMPLIANCE
    STATUS  current
    DESCRIPTION
        "The compliance statement for management of Filter features
         on Nokia SROS series systems release R14.0."
    MODULE  -- this module
        MANDATORY-GROUPS {
            tFilterScalarGroup,
            tIPFilterV14v0Group,
            tIPFilterV13v0Group,
            tMacFilterV8v0Group,
            tFilterLogGroup,
            tFilterLogV5v0Group,
            tFilterRedirectPolicyV13v0Group,
            tFilterNotificationsV11v0Group,
            tFilterNotificationsV12v0Group,
            tFilterNotificationObjV12v0Group,
            tIPv6FilterV14v0Group,
            tIPv6FilterV13v0Group,
            tMacFilterVidFilteringV9v0Group,
            tDhcpFilterV10v0Group,
            tDhcpFilterV13v0Group,
            tFilterNameV10v0Group,
            tLiFilterV12v0Group,
            tFilterPrefixListV11v0Group,
            tFilterEmbeddedInsertV11v0Group,
            tFilterEmbeddedInsertV12v0Group,
            tFilterEmbeddedInsertV13v0Group,
            tFilterPortListV11v0Group,
            tFilterSystemFilterV13v0Group,
            tMacFilterV13v0Group,
            tFilterEmbedFlowspecGroup,
            tFilterNotificationsV14v0Group,
            tFilterIPvXRedundantActionGroup,
            tFilterMacRedundantActionGroup,
            tFilterEmbedVsdGroup,
            tFilterEntryStatGroup,
            tFilterEmbeddedRefGroup,
            tFilterRemarkDscpGroup,
            tFilterRemarkDscpExtGroup,
            tFilterPrefListInfoGroup
        }
    ::= { tFilterMIBCompliances 17 }
--
-- Units of conformance
--

-- tIPFilterGroup OBJECT-GROUP
--    ::= { tFilterMIBGroups 1 }

-- tMacFilterGroup OBJECT-GROUP
--    ::= { tFilterMIBGroups 2 }

tFilterLogGroup OBJECT-GROUP
    OBJECTS {
                tFilterLogRowStatus,
                tFilterLogDestination,
                tFilterLogDescription,
                tFilterLogMaxNumEntries,
                tFilterLogSysLogId,
                tFilterLogFileId,
                tFilterLogStopOnFull,
                tFilterLogEnabled,
                tFilterLogMaxInstances,
                tFilterLogInstances,
                tFilterLogBindings
            }
    STATUS    current
    DESCRIPTION
        "The group of objects supporting management of filter log objects
        on Nokia SROS series systems."
    ::= { tFilterMIBGroups 3 }

tFilterRedirectPolicyGroup OBJECT-GROUP
    OBJECTS {
                tFilterRPRowStatus,
                tFilterRPDescription,
                tFilterRPAdminState,
                tFilterRPActiveDest,

                tFilterRDRowStatus,
                tFilterRDDescription,
                tFilterRDAdminPriority,
                tFilterRDOperPriority,
                tFilterRDAdminState,
                tFilterRDOperState,

                tFilterRSTRowStatus,
                tFilterRSTOID,
                tFilterRSTCommunity,
                tFilterRSTSNMPVersion,
                tFilterRSTInterval,
                tFilterRSTTimeout,
                tFilterRSTDropCount,
                tFilterRSTHoldDown,
                tFilterRSTHoldDownRemain,
                tFilterRSTLastActionTime,
                tFilterRSTLastOID,
                tFilterRSTLastType,
                tFilterRSTLastCounter32Val,
                tFilterRSTLastUnsigned32Val,
                tFilterRSTLastTimeTicksVal,
                tFilterRSTLastInt32Val,
                tFilterRSTLastOctetStringVal,
                tFilterRSTLastIpAddressVal,
                tFilterRSTLastOidVal,
                tFilterRSTLastCounter64Val,
                tFilterRSTLastOpaqueVal,
                tFilterRSTLastAction,
                tFilterRSTLastPrioChange,
                tFilterRSTNextRespIndex,

                tFilterRSTRespRowStatus,
                tFilterRSTRespAction,
                tFilterRSTRespPrioChange,
                tFilterRSTRespOID,
                tFilterRSTRespType,
                tFilterRSTCounter32Val,
                tFilterRSTUnsigned32Val,
                tFilterRSTTimeTicksVal,
                tFilterRSTInt32Val,
                tFilterRSTOctetStringVal,
                tFilterRSTIpAddressVal,
                tFilterRSTOidVal,
                tFilterRSTCounter64Val,
                tFilterRSTOpaqueVal,

                tFilterRUTRowStatus,
                tFilterRUTURL,
                tFilterRUTHTTPVersion,
                tFilterRUTInterval,
                tFilterRUTTimeout,
                tFilterRUTDropCount,
                tFilterRUTHoldDown,
                tFilterRUTHoldDownRemain,
                tFilterRUTLastActionTime,
                tFilterRUTLastRetCode,
                tFilterRUTLastAction,
                tFilterRUTLastPrioChange,

                tFilterRUTRespRowStatus,
                tFilterRUTRespAction,
                tFilterRUTRespPrioChange,

                tFilterRPTRowStatus,
                tFilterRPTInterval,
                tFilterRPTTimeout,
                tFilterRPTDropCount,
                tFilterRPTHoldDown,
                tFilterRPTHoldDownRemain,
                tFilterRPTLastActionTime,
                tFilterRPTLastAction
            }
    STATUS    obsolete
    DESCRIPTION
        "The group of objects supporting management of filter redirect policy
         objects on Nokia SROS series systems.
         This group is obsoleted in release 13.0."
    ::= { tFilterMIBGroups 4 }

tFilterScalarGroup OBJECT-GROUP
    OBJECTS {
                tFilterDomainLastChanged
            }
    STATUS    current
    DESCRIPTION
        "The group of objects supporting management of filter scalar
         objects on Nokia SROS series systems."
    ::= { tFilterMIBGroups 7 }

tFilterNotificationObjGroup OBJECT-GROUP
    OBJECTS {
                tFilterPBRDropReason
            }
    STATUS    obsolete
    DESCRIPTION
         "The group of objects supporting management of filter
          notification objects on Nokia SROS series systems."
    ::= { tFilterMIBGroups 8 }

tFilterNotificationsGroup NOTIFICATION-GROUP
     NOTIFICATIONS {
                 tIPFilterPBRPacketsDrop
                   }
     STATUS obsolete
     DESCRIPTION
         "The group of notifications supporting management of
          filter notifications on Nokia SROS series systems."
     ::= { tFilterMIBGroups 9 }

-- tAutoIPFilterR2r1Group OBJECT-GROUP
--    ::= { tFilterMIBGroups 10 }

tIPv6FilterV4v0Group OBJECT-GROUP
    OBJECTS {
                tIPv6FilterRowStatus,
                tIPv6FilterScope,
                tIPv6FilterDescription,
                tIPv6FilterDefaultAction,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest
            }
    STATUS obsolete
    DESCRIPTION
        "The group of objects supporting management of IPv6 filter objects
         on Nokia SROS series systems."
    ::= { tFilterMIBGroups 11 }

tIPFilterV4v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL
            }
    STATUS obsolete
    DESCRIPTION
        "The group of objects supporting IP Filters
         on Nokia 7x50 ESS/SR series systems 4.0 release."
    ::= { tFilterMIBGroups 12 }

tMacFilterV4v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL
            }
    STATUS obsolete
    DESCRIPTION
        "The group of objects supporting management of mac filter objects
         on Nokia SROS series systems 4.0 release."
    ::= { tFilterMIBGroups 13 }

tTodPoliciesV4v0Group OBJECT-GROUP
    OBJECTS {
                tIPFilterParamsTimeRangeName,
                tIPFilterParamsTimeRangeState,
                tMacFilterParamsTimeRangeName,
                tMacFilterParamsTimeRangeState,
                tIPv6FilterParamsTimeRangeName,
                tIPv6FilterParamsTimeRangeState
            }
    STATUS obsolete
    DESCRIPTION
        "The group of objects supporting management of time of day policy
         related objects on Nokia SROS series systems 4.0 release."
    ::= { tFilterMIBGroups 14 }

tmnxFilterObsoleteGroup OBJECT-GROUP
    OBJECTS {
                tAutoIPFilterEntrySourceIpMask
            }
    STATUS current
    DESCRIPTION
        "The group of objects in TIMETRA-FILTER-MIB which are obsoleted."
    ::= { tFilterMIBGroups 15 }

tToDPoliciesV5v0NotifyGroup NOTIFICATION-GROUP
     NOTIFICATIONS {
                 tFilterEntryActivationFailed,
                 tFilterEntryActivationRestored
            }
     STATUS obsolete
     DESCRIPTION
        "The group of notifications generated by the time of time of day
         policy feature on Nokia SROS series systems 5.0 release."
     ::= { tFilterMIBGroups 16 }

tIPFilterV5v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask
            }
    STATUS obsolete
    DESCRIPTION
        "The group of objects supporting IP Filters
         on Nokia 7x50 ESS/SR series systems 5.0 release."
    ::= { tFilterMIBGroups 17 }

tFilterLogV5v0Group OBJECT-GROUP
    OBJECTS {
                tFilterLogSummaryEnabled,
                tFilterLogSummaryCrit1
            }
    STATUS current
    DESCRIPTION
        "The group of objects supporting Filter Log Summarization
         on Nokia 7x50 ESS/SR series systems 5.0 release."
    ::= { tFilterMIBGroups 18 }

tTodPolicies77450V5v0Group OBJECT-GROUP
    OBJECTS {
                tIPFilterParamsTimeRangeName,
                tIPFilterParamsTimeRangeState,
                tMacFilterParamsTimeRangeName,
                tMacFilterParamsTimeRangeState
            }
    STATUS obsolete
    DESCRIPTION
        "The group of objects supporting management of time of day policy
         related objects on Nokia 7450 ESS series systems 5.0 release.

        This group was made obsolete for Nokia SROS Release 9.0."
    ::= { tFilterMIBGroups 19 }

tTodPolicies77x0V5v0Group OBJECT-GROUP
    OBJECTS {
                tIPFilterParamsTimeRangeName,
                tIPFilterParamsTimeRangeState,
                tMacFilterParamsTimeRangeName,
                tMacFilterParamsTimeRangeState,
                tIPv6FilterParamsTimeRangeName,
                tIPv6FilterParamsTimeRangeState
            }
    STATUS obsolete
    DESCRIPTION
        "The group of objects supporting management of time of day policy
         related objects on Nokia 77x0 series systems 5.0 release."
    ::= { tFilterMIBGroups 20 }

tFilterNotificationObjV5v0Group OBJECT-GROUP
    OBJECTS {
                tFilterPBRDropReason,
                tFilterParmRow,
                tFilterAlarmDescription
            }
    STATUS obsolete
    DESCRIPTION
         "The group of objects supporting management of filter
          notification objects on Nokia SROS series systems."
    ::= { tFilterMIBGroups 21 }

tIPFilterV6v0Group OBJECT-GROUP
    OBJECTS {
                tIPFilterRowStatus,
                tIPFilterScope,
                tIPFilterDescription,
                tIPFilterDefaultAction,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount
            }
    STATUS obsolete
    DESCRIPTION
        "The group of objects supporting IP Filters
         on Nokia 7x50 ESS/SR series systems 6.0 release."
    ::= { tFilterMIBGroups 22 }

tMacFilterV6v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL,
                tMacFilterParamsIngrHitByteCount,
                tMacFilterParamsEgrHitByteCount
            }
    STATUS obsolete
    DESCRIPTION
        "The group of objects supporting management of mac filter objects
         on Nokia SROS series systems 6.0 release."
    ::= { tFilterMIBGroups 23 }

tIPv6FilterV6v0Group OBJECT-GROUP
    OBJECTS {
                tIPv6FilterRowStatus,
                tIPv6FilterScope,
                tIPv6FilterDescription,
                tIPv6FilterDefaultAction,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount
            }
    STATUS obsolete
    DESCRIPTION
        "The group of objects supporting management of IPv6 filter objects
         on Nokia SROS series systems."
    ::= { tFilterMIBGroups 24 }

tIPFilterV8v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute
            }
    STATUS obsolete
    DESCRIPTION
        "The group of objects supporting IP Filters
         on Nokia 7x50 ESS/SR series systems 8.0 release."
    ::= { tFilterMIBGroups 25 }

tIPv6FilterV8v0Group OBJECT-GROUP
    OBJECTS {
                tIPv6FilterRowStatus,
                tIPv6FilterScope,
                tIPv6FilterDescription,
                tIPv6FilterDefaultAction,
                tIPv6FilterRadiusInsertPt,
                tIPv6FilterRadiusInsertSize,
                tIPv6FilterCreditCntrlInsertPt,
                tIPv6FilterCreditCntrlInsertSize,
                tIPv6FilterSubInsertHighWmark,
                tIPv6FilterSubInsertLowWmark,
                tIpv6FilterCreditCntrlNbrInsertd,
                tIpv6FilterRadiusNbrInsertd,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount
            }
    STATUS obsolete
    DESCRIPTION
        "The group of objects supporting management of IPv6 filter objects
         on Nokia SROS series systems."
    ::= { tFilterMIBGroups 26 }

tFilterNotificationObjV8v0Group OBJECT-GROUP
    OBJECTS {
                tFilterPBRDropReason,
                tFilterParmRow,
                tFilterAlarmDescription,
                tFilterId,
                tFilterType,
                tFilterSubInsSpaceOwner,
                tFilterThresholdReached
            }
    STATUS obsolete
    DESCRIPTION
         "The group of objects supporting management of filter
          notification objects on Nokia SROS series systems."
    ::= { tFilterMIBGroups 27 }

tFilterNotificationsV8v0Group NOTIFICATION-GROUP
     NOTIFICATIONS {
                 tIPFilterPBRPacketsDrop,
                 tFilterSubInsSpaceAlarmRaised,
                 tFilterSubInsSpaceAlarmCleared,
                 tFilterSubInsFltrEntryDropped
            }
     STATUS obsolete
     DESCRIPTION
         "The group of notifications supporting management of
          filter notifications on Nokia SROS series systems."
     ::= { tFilterMIBGroups 28 }

tMacFilterV8v0Group OBJECT-GROUP
    OBJECTS {
                tMacFilterRowStatus,
                tMacFilterScope,
                tMacFilterDescription,
                tMacFilterDefaultAction,
                tMacFilterParamsRowStatus,
                tMacFilterParamsLogId,
                tMacFilterParamsDescription,
                tMacFilterParamsAction,
                tMacFilterParamsFrameType,
                tMacFilterParamsSrcMAC,
                tMacFilterParamsSrcMACMask,
                tMacFilterParamsDstMAC,
                tMacFilterParamsDstMACMask,
                tMacFilterParamsDot1pValue,
                tMacFilterParamsDot1pMask,
                tMacFilterParamsEtherType,
                tMacFilterParamsDsap,
                tMacFilterParamsDsapMask,
                tMacFilterParamsSsap,
                tMacFilterParamsSsapMask,
                tMacFilterParamsSnapPid,
                tMacFilterParamsSnapOui,
                tMacFilterParamsIngressHitCount,
                tMacFilterParamsEgressHitCount,
                tMacFilterParamsLogInstantiated,
                tMacFilterParamsFwdSvcId,
                tMacFilterParamsFwdSapPortId,
                tMacFilterParamsFwdSapEncapVal,
                tMacFilterParamsFwdSdpBind,
                tMacFilterParamsRedirectURL,
                tMacFilterParamsIngrHitByteCount,
                tMacFilterParamsEgrHitByteCount,
                tMacFilterParamsLowISID,
                tMacFilterParamsHighISID,
                tMacFilterType
            }
    STATUS current
    DESCRIPTION
     "The group of objects supporting management of mac filter objects
     on Nokia SROS series systems 8.0 release."
    ::= { tFilterMIBGroups 29 }

tMacFilterVidFilteringV9v0Group OBJECT-GROUP
    OBJECTS {
                tMacFilterParamsInnerTagValue,
                tMacFilterParamsInnerTagMask,
                tMacFilterParamsOuterTagValue,
                tMacFilterParamsOuterTagMask
            }
    STATUS current
    DESCRIPTION
     "The group of objects supporting management of mac VID filtering objects
      on Nokia SROS series systems 9.0 release."
    ::= { tFilterMIBGroups 30 }

tIPFilterV9v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption
            }
    STATUS obsolete
    DESCRIPTION
        "The group of objects supporting IP Filters
         on Nokia 7x50 ESS/SR series systems 9.0 release."
    ::= { tFilterMIBGroups 31 }

tFilterNotificationsV9v0Group NOTIFICATION-GROUP
     NOTIFICATIONS {
                 tIPFilterPBRPacketsDrop,
                 tFilterSubInsSpaceAlarmRaised,
                 tFilterSubInsSpaceAlarmCleared,
                 tFilterSubInsFltrEntryDropped,
                 tFilterBgpFlowSpecProblem
            }
     STATUS obsolete
     DESCRIPTION
         "The group of notifications supporting management of
          filter notifications on Nokia SROS series systems."
     ::= { tFilterMIBGroups 32 }

tFilterNotificationObjV9v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId
            }
    STATUS    obsolete
    DESCRIPTION
         "The group of objects supporting management of filter
          notification objects on Nokia SROS series systems."
    ::= { tFilterMIBGroups 33 }

tDhcpFilterV9v0Group OBJECT-GROUP
    OBJECTS {
                tDhcpFilterTableLastChanged,
                tDhcpFilterRowStatus,
                tDhcpFilterLastChanged,
                tDhcpFilterDescription,
                tDhcpFilterParamsTblLastChanged,
                tDhcpFilterParamsRowStatus,
                tDhcpFilterParamsLastChanged,
                tDhcpFilterParamsOptionNumber,
                tDhcpFilterParamsOptionMatch,
                tDhcpFilterParamsAction
            }
    STATUS    obsolete
    DESCRIPTION
        "The group of objects supporting DHCP Filters
         on Nokia 7x50 ESS/SR series systems 9.0 release."
    ::= { tFilterMIBGroups 34 }

tIPv6FilterV10v0Group OBJECT-GROUP
    OBJECTS {
                tIPv6FilterRowStatus,
                tIPv6FilterScope,
                tIPv6FilterDescription,
                tIPv6FilterDefaultAction,
                tIPv6FilterRadiusInsertPt,
                tIPv6FilterRadiusInsertSize,
                tIPv6FilterCreditCntrlInsertPt,
                tIPv6FilterCreditCntrlInsertSize,
                tIPv6FilterSubInsertHighWmark,
                tIPv6FilterSubInsertLowWmark,
                tIpv6FilterCreditCntrlNbrInsertd,
                tIpv6FilterRadiusNbrInsertd,
                tIPv6FilterParamsRowStatus,
                tIPv6FilterParamsLogId,
                tIPv6FilterParamsDescription,
                tIPv6FilterParamsAction,
                tIPv6FilterParamsForwardNH,
                tIPv6FilterParamsForwardNHIndirect,
                tIPv6FilterParamsRemarkDSCP,
                tIPv6FilterParamsRemarkDSCPMask,
                tIPv6FilterParamsRemarkDot1p,
                tIPv6FilterParamsSourceIpAddr,
                tIPv6FilterParamsSourceIpMask,
                tIPv6FilterParamsDestinationIpAddr,
                tIPv6FilterParamsDestinationIpMask,
                tIPv6FilterParamsNextHeader,
                tIPv6FilterParamsSourcePortValue1,
                tIPv6FilterParamsSourcePortValue2,
                tIPv6FilterParamsSourcePortOperator,
                tIPv6FilterParamsDestPortValue1,
                tIPv6FilterParamsDestPortValue2,
                tIPv6FilterParamsDestPortOperator,
                tIPv6FilterParamsDSCP,
                tIPv6FilterParamsTcpSyn,
                tIPv6FilterParamsTcpAck,
                tIPv6FilterParamsIcmpCode,
                tIPv6FilterParamsIcmpType,
                tIPv6FilterParamsCflowdSample,
                tIPv6FilterParamsCflowdIfSample,
                tIPv6FilterParamsForwardNHInterface,
                tIPv6FilterParamsIngressHitCount,
                tIPv6FilterParamsEgressHitCount,
                tIPv6FilterParamsLogInstantiated,
                tIPv6FilterParamsForwardRedPlcy,
                tIPv6FilterParamsActiveDest,
                tIPv6FilterParamsIngrHitByteCount,
                tIPv6FilterParamsEgrHitByteCount,
                tIPv6FilterParamsFwdSvcId,
                tIPv6FilterParamsFwdSapPortId,
                tIPv6FilterParamsFwdSapEncapVal,
                tIPv6FilterParamsFwdSdpBind
            }
    STATUS obsolete
    DESCRIPTION
        "The group of objects supporting management of IPv6 filter objects
         on Nokia SROS series systems."
    ::= { tFilterMIBGroups 35 }

tFilterNameV10v0Group OBJECT-GROUP
    OBJECTS {
         tIpFilterName,
         tIpFilterNameId,
         tIpFilterNameLastChanged,
         tIpFilterNameRowStatus,
         tIpFilterNameTableLastChgd,
         tIpv6FilterName,
         tIpv6FilterNameId,
         tIpv6FilterNameLastChanged,
         tIpv6FilterNameRowStatus,
         tIpv6FilterNameTableLastChgd,
         tMacFilterName,
         tMacFilterNameId,
         tMacFilterNameLastChanged,
         tMacFilterNameRowStatus,
         tMacFilterNameTableLastChgd
    }
    STATUS  current
    DESCRIPTION
        "The group of objects supporting management of filter-name objects
         on Nokia SROS series systems."
    ::= { tFilterMIBGroups 36 }

tDhcpFilterV10v0Group OBJECT-GROUP
    OBJECTS {
                tDhcpFilterTableLastChanged,
                tDhcpFilterRowStatus,
                tDhcpFilterLastChanged,
                tDhcpFilterDescription,
                tDhcpFilterParamsTblLastChanged,
                tDhcpFilterParamsRowStatus,
                tDhcpFilterParamsLastChanged,
                tDhcpFilterParamsOptionNumber,
                tDhcpFilterParamsOptionMatch,
                tDhcpFilterParamsAction,
                tDhcpFilterParamsOptionValue
            }
    STATUS    current
    DESCRIPTION
        "The group of objects supporting DHCP Filters
         on Nokia 7x50 ESS/SR series systems 10.0 release."
    ::= { tFilterMIBGroups 37 }

tLiFilterV10v0Group OBJECT-GROUP
    OBJECTS {
        tLiReservedBlockRowStatus,
        tLiReservedBlockDescription,
        tLiReservedBlockStart,
        tLiReservedBlockSize,
        tLiReservedBlockLastChanged,
        tLiReservedBlockTableLastChanged,
        tLiReservedBlockFltrRowStatus,
        tLiReservedBlockFltrLastChanged,
        tLiReservedBlockFltrTableLastChg,
        tLiFilterDescription,
        tLiFilterRowStatus,
        tLiFilterLastChanged,
        tLiFilterTableLastChanged,
        tLiFilterAssociationRowStatus,
        tLiFilterAssociationLastChg,
        tLiFilterAssociationTableLastChg,
        tLiMacFilterParamsDescription,
        tLiMacFilterParamsDstMAC,
        tLiMacFilterParamsDstMACMask,
        tLiMacFilterParamsFrameType,
        tLiMacFilterParamsRowStatus,
        tLiMacFilterParamsSrcMAC,
        tLiMacFilterParamsSrcMACMask,
        tLiMacFilterParamsLastChanged,
        tLiMacFilterParamsTableLastChg,
        tLiMacFilterParamsIngrHitCount,
        tLiMacFilterParamsEgrHitCount,
        tLiMacFilterParamsIngrHitBytes,
        tLiMacFilterParamsEgrHitBytes
    }
    STATUS    obsolete
    DESCRIPTION
        "The group of objects supporting management of LI filter entries
         on Nokia SROS series systems 10.0 release."
    ::= { tFilterMIBGroups 38 }

tFilterPrefixListV10v0Group OBJECT-GROUP
    OBJECTS {
        tFilterPrefixListTableLstChng,
        tFilterPrefixListRowStatus,
        tFilterPrefixListLastChanged,
        tFilterPrefixListDescription,
        tFilterPrefixListEntryTblLstChg,
        tFilterPrefixListEntryRowStatus,
        tIPFilterParamsSrcIpPrefixList,
        tIPFilterParamsDstIpPrefixList
    }
    STATUS    obsolete
    DESCRIPTION
        "The group of objects supporting management of IP prefix lists
        in IP filters on Nokia SROS series systems
        10.0 release."
    ::= { tFilterMIBGroups 39 }

tIPv6FilterV11v0Group OBJECT-GROUP
    OBJECTS {
        tIPv6FilterRowStatus,
        tIPv6FilterScope,
        tIPv6FilterDescription,
        tIPv6FilterDefaultAction,
        tIPv6FilterRadiusInsertPt,
        tIPv6FilterRadiusInsertSize,
        tIPv6FilterCreditCntrlInsertPt,
        tIPv6FilterCreditCntrlInsertSize,
        tIPv6FilterSubInsertHighWmark,
        tIPv6FilterSubInsertLowWmark,
        tIpv6FilterCreditCntrlNbrInsertd,
        tIpv6FilterRadiusNbrInsertd,
        tIPv6FilterHostSharedInsertPt,
        tIPv6FilterHostSharedInsertSize,
        tIpv6FilterHostSharedNbrInsertd,
        tIPv6FilterHostSharedHighWmark,
        tIPv6FilterHostSharedLowWmark,
        tIPv6FilterNbrHostSharedFltrs,
        tIPv6FilterParamsRowStatus,
        tIPv6FilterParamsLogId,
        tIPv6FilterParamsDescription,
        tIPv6FilterParamsAction,
        tIPv6FilterParamsForwardNH,
        tIPv6FilterParamsForwardNHIndirect,
        tIPv6FilterParamsRemarkDSCP,
        tIPv6FilterParamsRemarkDSCPMask,
        tIPv6FilterParamsRemarkDot1p,
        tIPv6FilterParamsSourceIpAddr,
        tIPv6FilterParamsSourceIpMask,
        tIPv6FilterParamsDestinationIpAddr,
        tIPv6FilterParamsDestinationIpMask,
        tIPv6FilterParamsNextHeader,
        tIPv6FilterParamsSourcePortValue1,
        tIPv6FilterParamsSourcePortValue2,
        tIPv6FilterParamsSourcePortOperator,
        tIPv6FilterParamsDestPortValue1,
        tIPv6FilterParamsDestPortValue2,
        tIPv6FilterParamsDestPortOperator,
        tIPv6FilterParamsDSCP,
        tIPv6FilterParamsTcpSyn,
        tIPv6FilterParamsTcpAck,
        tIPv6FilterParamsIcmpCode,
        tIPv6FilterParamsIcmpType,
        tIPv6FilterParamsCflowdSample,
        tIPv6FilterParamsCflowdIfSample,
        tIPv6FilterParamsForwardNHInterface,
        tIPv6FilterParamsIngressHitCount,
        tIPv6FilterParamsEgressHitCount,
        tIPv6FilterParamsLogInstantiated,
        tIPv6FilterParamsForwardRedPlcy,
        tIPv6FilterParamsActiveDest,
        tIPv6FilterParamsIngrHitByteCount,
        tIPv6FilterParamsEgrHitByteCount,
        tIPv6FilterParamsFwdSvcId,
        tIPv6FilterParamsFwdSapPortId,
        tIPv6FilterParamsFwdSapEncapVal,
        tIPv6FilterParamsFwdSdpBind,
        tIPv6FilterParamsRedirectURL,
        tIPv6FilterParamsSrcIpPrefixList,
        tIPv6FilterParamsDstIpPrefixList,
        tIPv6FilterParamsFragment,
        tIPv6FilterParamsHopByHopOpt,
        tIPv6FilterParamsRoutingType0,
        tIPv6FilterParamsPortSelector,
        tIPv6FilterParamsSrcPortList,
        tIPv6FilterParamsDstPortList,
        tIPv6FilterParamsFwdRtrId
    }
    STATUS    obsolete
    DESCRIPTION
        "The group of objects supporting management of IPv6 filter objects
        on Nokia SROS series systems."
    ::= { tFilterMIBGroups 40 }

tFilterEmbeddedInsertV11v0Group OBJECT-GROUP
    OBJECTS {
        tFilterEmbeddedRefRowStatus      ,
        tFilterEmbeddedRefTableLstChg    ,
        tFilterEmbeddedRefOperState      ,
        tFilterEmbeddedRefAdminState     ,
        tFltrEmbedRefInfEntryCnt         ,
        tFltrEmbedRefInfEntryCntInsrtd   ,
        tFltrEmbedEntryInsrtEntryId      ,
        tFltrEmbedEntryRefOperState
    }
    STATUS current
    DESCRIPTION
        "The group of objects supporting the creation of embedded filters
         for Nokia SROS systems 11.0 release."
    ::= { tFilterMIBGroups 41 }

tFilterPortListV11v0Group OBJECT-GROUP
    OBJECTS {
        tFilterPortListTableLstChng,
        tFilterPortListRowStatus,
        tFilterPortListLastChanged,
        tFilterPortListDescription,
        tFilterPortListEntryTblLstChg,
        tFilterPortListEntryRowStatus
    }
    STATUS    current
    DESCRIPTION
        "The group of objects supporting the management of port lists
         for filters on Nokia SROS series systems 11.0 release."
    ::= { tFilterMIBGroups 42 }

tFilterPrefixListV11v0Group OBJECT-GROUP
    OBJECTS {
        tFilterPrefixListTableLstChng,
        tFilterPrefixListRowStatus,
        tFilterPrefixListLastChanged,
        tFilterPrefixListDescription,
        tFilterPrefixListEntryTblLstChg,
        tFilterPrefixListEntryRowStatus,
        tIPFilterParamsSrcIpPrefixList,
        tIPFilterParamsDstIpPrefixList,
        tFilterApplyPathTableLstChng,
        tFilterApplyPathRowStatus,
        tFilterApplyPathLastChanged,
        tFilterApplyPathMatch1,
        tFilterApplyPathMatch2
    }
    STATUS    current
    DESCRIPTION
        "The group of objects supporting management of IP prefix lists
        in IP filters on Nokia SROS series systems
        11.0 release."
    ::= { tFilterMIBGroups 43 }

tIPFilterV11v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterHostSharedInsertPt,
                tIPFilterHostSharedInsertSize,
                tIpFilterHostSharedNbrInsertd,
                tIPFilterHostSharedHighWmark,
                tIPFilterHostSharedLowWmark,
                tIPFilterNbrHostSharedFltrs,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption,
                tIPFilterParamsPortSelector,
                tIPFilterParamsSrcPortList,
                tIPFilterParamsDstPortList,
                tIPFilterParamsExtTbleLstChgd,
                tIPFilterParamsExtLastChanged,
                tIPFilterParamsExtPktLenVal1,
                tIPFilterParamsExtPktLenVal2,
                tIPFilterParamsExtPktLenOper
            }
    STATUS    obsolete
    DESCRIPTION
        "The group of objects supporting IP Filters
         on Nokia 7x50 ESS/SR series systems 11.0 release."
    ::= { tFilterMIBGroups 44 }

tFilterNotificationsV11v0Group NOTIFICATION-GROUP
     NOTIFICATIONS {
                 tIPFilterPBRPacketsDrop,
                 tFilterSubInsSpaceAlarmRaised,
                 tFilterSubInsSpaceAlarmCleared,
                 tFilterSubInsFltrEntryDropped,
                 tFilterBgpFlowSpecProblem,
                 tFilterApplyPathProblem,
                 tFilterRadSharedFltrAlarmRaised,
                 tFilterRadSharedFltrAlarmClear,
                 tFilterEmbeddingOperStateChange
            }
     STATUS current
     DESCRIPTION
         "The group of notifications supporting management of
          filter notifications on Nokia SROS series systems."
     ::= { tFilterMIBGroups 45 }

tFilterNotificationObjV11v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId,
                tFltrPrefixListType,
                tFltrPrefixListName,
                tFltrApplyPathSource,
                tFltrApplyPathIndex,
                tFltrNotifDescription
            }
    STATUS    obsolete
    DESCRIPTION
         "The group of objects supporting management of filter
         notification objects on Nokia SROS series systems."
    ::= { tFilterMIBGroups 46 }

tIPFilterV12v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterHostSharedInsertPt,
                tIPFilterHostSharedInsertSize,
                tIpFilterHostSharedNbrInsertd,
                tIPFilterHostSharedHighWmark,
                tIPFilterHostSharedLowWmark,
                tIPFilterNbrHostSharedFltrs,
                tIPFilterParamsRowStatus,
                tIPFilterParamsLogId,
                tIPFilterParamsDescription,
                tIPFilterParamsAction,
                tIPFilterParamsForwardNH,
                tIPFilterParamsForwardNHIndirect,
                tIPFilterParamsRemarkDSCP,
                tIPFilterParamsRemarkDSCPMask,
                tIPFilterParamsRemarkDot1p,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption,
                tIPFilterParamsPortSelector,
                tIPFilterParamsSrcPortList,
                tIPFilterParamsDstPortList,
                tIPFilterParamsExtTbleLstChgd,
                tIPFilterParamsExtLastChanged,
                tIPFilterParamsExtPktLenVal1,
                tIPFilterParamsExtPktLenVal2,
                tIPFilterParamsExtPktLenOper,
                tIPFilterParamsRdirAllwRadOvrd,
                tIPFilterParamsNatPolicyName,
                tIPFilterParamsFwdLsp,
                tIPFilterParamsFwdLspRtrId
            }
    STATUS    obsolete
    DESCRIPTION
        "The group of objects supporting IP Filters
         on Nokia 7x50 ESS/SR series systems 12.0 release.
         This group was made obsolete in release 14.0."
    ::= { tFilterMIBGroups 47 }

tIPv6FilterV12v0Group OBJECT-GROUP
    OBJECTS {
        tIPv6FilterRowStatus,
        tIPv6FilterScope,
        tIPv6FilterDescription,
        tIPv6FilterDefaultAction,
        tIPv6FilterRadiusInsertPt,
        tIPv6FilterRadiusInsertSize,
        tIPv6FilterCreditCntrlInsertPt,
        tIPv6FilterCreditCntrlInsertSize,
        tIPv6FilterSubInsertHighWmark,
        tIPv6FilterSubInsertLowWmark,
        tIpv6FilterCreditCntrlNbrInsertd,
        tIpv6FilterRadiusNbrInsertd,
        tIPv6FilterHostSharedInsertPt,
        tIPv6FilterHostSharedInsertSize,
        tIpv6FilterHostSharedNbrInsertd,
        tIPv6FilterHostSharedHighWmark,
        tIPv6FilterHostSharedLowWmark,
        tIPv6FilterNbrHostSharedFltrs,
        tIPv6FilterParamsRowStatus,
        tIPv6FilterParamsLogId,
        tIPv6FilterParamsDescription,
        tIPv6FilterParamsAction,
        tIPv6FilterParamsForwardNH,
        tIPv6FilterParamsForwardNHIndirect,
        tIPv6FilterParamsRemarkDSCP,
        tIPv6FilterParamsRemarkDSCPMask,
        tIPv6FilterParamsRemarkDot1p,
        tIPv6FilterParamsSourceIpAddr,
        tIPv6FilterParamsSourceIpMask,
        tIPv6FilterParamsDestinationIpAddr,
        tIPv6FilterParamsDestinationIpMask,
        tIPv6FilterParamsNextHeader,
        tIPv6FilterParamsSourcePortValue1,
        tIPv6FilterParamsSourcePortValue2,
        tIPv6FilterParamsSourcePortOperator,
        tIPv6FilterParamsDestPortValue1,
        tIPv6FilterParamsDestPortValue2,
        tIPv6FilterParamsDestPortOperator,
        tIPv6FilterParamsDSCP,
        tIPv6FilterParamsTcpSyn,
        tIPv6FilterParamsTcpAck,
        tIPv6FilterParamsIcmpCode,
        tIPv6FilterParamsIcmpType,
        tIPv6FilterParamsCflowdSample,
        tIPv6FilterParamsCflowdIfSample,
        tIPv6FilterParamsForwardNHInterface,
        tIPv6FilterParamsIngressHitCount,
        tIPv6FilterParamsEgressHitCount,
        tIPv6FilterParamsLogInstantiated,
        tIPv6FilterParamsForwardRedPlcy,
        tIPv6FilterParamsActiveDest,
        tIPv6FilterParamsIngrHitByteCount,
        tIPv6FilterParamsEgrHitByteCount,
        tIPv6FilterParamsFwdSvcId,
        tIPv6FilterParamsFwdSapPortId,
        tIPv6FilterParamsFwdSapEncapVal,
        tIPv6FilterParamsFwdSdpBind,
        tIPv6FilterParamsRedirectURL,
        tIPv6FilterParamsSrcIpPrefixList,
        tIPv6FilterParamsDstIpPrefixList,
        tIPv6FilterParamsFragment,
        tIPv6FilterParamsHopByHopOpt,
        tIPv6FilterParamsRoutingType0,
        tIPv6FilterParamsPortSelector,
        tIPv6FilterParamsSrcPortList,
        tIPv6FilterParamsDstPortList,
        tIPv6FilterParamsRdirAllwRadOvrd,
        tIPv6FilterParamsFwdRtrId,
        tIPv6FilterParamsSrcIpFullMask,
        tIPv6FilterParamsDstIpFullMask,
        tIPv6FilterParamsNatPolicyName,
        tIPv6FilterParamsFlowLabel,
        tIPv6FilterParamsFlowLabelMask,
        tIPv6FilterParamsFwdLspRtrId,
        tIPv6FilterParamsFwdLsp,
        tIPv6FilterParamsExtTbleLstChgd,
        tIPv6FilterParamsExtLastChanged,
        tIPv6FilterParamsExtAhExtHdr,
        tIPv6FilterParamsExtEspExtHdr,
        tIPv6FilterParamsExtNatType
    }
    STATUS    obsolete
    DESCRIPTION
        "The group of objects supporting management of IPv6 filter objects
         on Nokia 7x50 ESS/SR series systems 12.0 release.
         This group was made obsolete in release 14.0."
    ::= { tFilterMIBGroups 48 }

tLiFilterV12v0Group OBJECT-GROUP
    OBJECTS {
        tLiReservedBlockRowStatus,
        tLiReservedBlockDescription,
        tLiReservedBlockStart,
        tLiReservedBlockSize,
        tLiReservedBlockLastChanged,
        tLiReservedBlockTableLastChanged,
        tLiReservedBlockFltrRowStatus,
        tLiReservedBlockFltrLastChanged,
        tLiReservedBlockFltrTableLastChg,
        tLiFilterDescription,
        tLiFilterRowStatus,
        tLiFilterLastChanged,
        tLiFilterTableLastChanged,
        tLiFilterAssociationRowStatus,
        tLiFilterAssociationLastChg,
        tLiFilterAssociationTableLastChg,
        tLiMacFilterParamsDescription,
        tLiMacFilterParamsDstMAC,
        tLiMacFilterParamsDstMACMask,
        tLiMacFilterParamsFrameType,
        tLiMacFilterParamsRowStatus,
        tLiMacFilterParamsSrcMAC,
        tLiMacFilterParamsSrcMACMask,
        tLiMacFilterParamsLastChanged,
        tLiMacFilterParamsTableLastChg,
        tLiMacFilterParamsIngrHitCount,
        tLiMacFilterParamsEgrHitCount,
        tLiMacFilterParamsIngrHitBytes,
        tLiMacFilterParamsEgrHitBytes,
        tLiIpFilterParamsTableLastChg,
        tLiIpFilterParamsLastChanged,
        tLiIpFilterParamsRowStatus,
        tLiIpFilterParamsDescription,
        tLiIpFilterParamsSrcIpAddrType,
        tLiIpFilterParamsSrcIpAddr,
        tLiIpFilterParamsSrcIpFullMask,
        tLiIpFilterParamsDstIpAddrType,
        tLiIpFilterParamsDstIpAddr,
        tLiIpFilterParamsDstIpFullMask,
        tLiIpFilterParamsProtocolNextHdr,
        tLiIpFilterParamsSrcPortValue1,
        tLiIpFilterParamsSrcPortValue2,
        tLiIpFilterParamsSrcPortOper,
        tLiIpFilterParamsDstPortValue1,
        tLiIpFilterParamsDstPortValue2,
        tLiIpFilterParamsDstPortOper,
        tLiIpFltrParamsInfIngrHitCount,
        tLiIpFltrParamsInfEgrHitCount,
        tLiIpFltrParamsInfIngrHitBytes,
        tLiIpFltrParamsInfEgrHitBytes
    }
    STATUS    current
    DESCRIPTION
        "The group of objects supporting management of LI filter entries
         on Nokia SROS series systems 12.0 release."
    ::= { tFilterMIBGroups 49 }
    
tFilterEmbeddedInsertV12v0Group OBJECT-GROUP
    OBJECTS {
        tFilterEmbedOpenflowRowStatus    ,
        tFilterEmbedOpenflowTableLstChg  ,
        tFilterEmbedOpenflowOperState    ,
        tFilterEmbedOpenflowAdminState   ,
        tFltrEmbedOfInfoEntryCnt         ,
        tFltrEmbedOfInfoEntryCntInsrtd   ,
        tFltrEmbedOfEntryInsrtEntryId    ,
        tFltrEmbedOfEntryInsrtEntryState  
    }
    STATUS current
    DESCRIPTION
        "The group of new objects supporting the creation of embedded filters
         for Nokia SROS systems 12.0 release."
    ::= { tFilterMIBGroups 50 }
         
tFilterNotificationsV12v0Group NOTIFICATION-GROUP
    NOTIFICATIONS {
        tFilterEmbedOpenflowOperStateChg,
        tFilterTmsEvent
    }
    STATUS current
    DESCRIPTION
        "The group of notifications supporting management of
         filter notifications on Nokia SROS series systems."
    ::= { tFilterMIBGroups 51 }

tFilterRedirectPolicyV13v0Group OBJECT-GROUP
    OBJECTS {
        tFilterRPVrtrId,
        tFilterRPRowStatus,
        tFilterRPDescription,
        tFilterRPAdminState,
        tFilterRPActiveDestAddrType,
        tFilterRPActiveDestAddr,
        tFilterRPDstStickiness,
        tFilterRPBestDstAddrType,
        tFilterRPBestDstAddr,
        tFilterRPStickinessHoldRemain,
        tFilterRPlcyDstTableLastChg,
        tFltrRPDstLastChanged,
        tFltrRPDstRowStatus,
        tFltrRPDstDescription,
        tFltrRPDstAdminPriority,
        tFltrRPDstOperPriority,
        tFltrRPDstAdminState,
        tFltrRPDstOperState,
        tFilterRPlcyPingTestTableLastChg,
        tFltrRPPingTLastChanged,
        tFltrRPPingTRowStatus,
        tFltrRPPingTInterval,
        tFltrRPPingTTimeout,
        tFltrRPPingTDropCount,
        tFltrRPPingTHoldDown,
        tFltrRPPingTHoldDownRemain,
        tFltrRPPingTLastActionTime,
        tFltrRPPingTLastAction,
        tFilterRPlcySNMPTestTableLastChg,
        tFltrRPSnmpTLastChanged,
        tFltrRPSnmpTRowStatus,
        tFltrRPSnmpTOID,
        tFltrRPSnmpTCommunity,
        tFltrRPSnmpTSnmpVersion,
        tFltrRPSnmpTInterval,
        tFltrRPSnmpTTimeout,
        tFltrRPSnmpTDropCount,
        tFltrRPSnmpTHoldDown,
        tFltrRPSnmpTHoldDownRemain,
        tFltrRPSnmpTLastActionTime,
        tFltrRPSnmpTLastOID,
        tFltrRPSnmpTLastType,
        tFltrRPSnmpTLastCounter32Val,
        tFltrRPSnmpTLastUnsigned32Val,
        tFltrRPSnmpTLastTimeTicksVal,
        tFltrRPSnmpTLastInt32Val,
        tFltrRPSnmpTLastOctetStringVal,
        tFltrRPSnmpTLastIpAddressVal,
        tFltrRPSnmpTLastOidVal,
        tFltrRPSnmpTLastCounter64Val,
        tFltrRPSnmpTLastOpaqueVal,
        tFltrRPSnmpTLastAction,
        tFltrRPSnmpTLastPrioChange,
        tFltrRPSnmpTNextRespIndex,
        tFilterRPlcySNMPRespTableLastChg,
        tFltrRPSnmpRspLastChanged,
        tFltrRPSnmpRspRowStatus,
        tFltrRPSnmpRspAction,
        tFltrRPSnmpRspPrioChange,
        tFltrRPSnmpRspOID,
        tFltrRPSnmpRspType,
        tFltrRPSnmpRspCounter32Val,
        tFltrRPSnmpRspUnsigned32Val,
        tFltrRPSnmpRspTimeTicksVal,
        tFltrRPSnmpRspInt32Val,
        tFltrRPSnmpRspOctetStringVal,
        tFltrRPSnmpRspIpAddressVal,
        tFltrRPSnmpRspOidVal,
        tFltrRPSnmpRspCounter64Val,
        tFltrRPSnmpRspOpaqueVal,
        tFilterRPlcyURLTestTableLastChg,
        tFltrRPUrlTLastChanged,
        tFltrRPUrlTRowStatus,
        tFltrRPUrlTUrl,
        tFltrRPUrlTHttpVersion,
        tFltrRPUrlTInterval,
        tFltrRPUrlTTimeout,
        tFltrRPUrlTDropCount,
        tFltrRPUrlTHoldDown,
        tFltrRPUrlTHoldDownRemain,
        tFltrRPUrlTLastActionTime,
        tFltrRPUrlTLastRetCode,
        tFltrRPUrlTLastAction,
        tFltrRPUrlTLastPrioChange,
        tFilterRPlcyURLRespTableLastChg,
        tFltrRPUrlTRspLastChanged,
        tFltrRPUrlTRspRowStatus,
        tFltrRPUrlTRspAction,
        tFltrRPUrlTRspPrioChange,
        tFilterRPlcyUcastRtTTableLastChg,
        tFltrRPUcastRtTLastChanged,
        tFltrRPUcastRtTRowStatus,
        tFltrRPUcastRtTLastActionTime,
        tFltrRPUcastRtTLastAction
    }
    STATUS    current
    DESCRIPTION
        "The group of objects supporting management of filter redirect policy
         objects on Nokia SROS series systems new in 13.0 series."
    ::= { tFilterMIBGroups 52 }

tFilterNotificationObjV12v0Group OBJECT-GROUP
    OBJECTS {
                tFilterPBRDropReason,
                tFilterParmRow,
                tFilterAlarmDescription,
                tFilterId,
                tFilterType,
                tFilterSubInsSpaceOwner,
                tFilterThresholdReached,
                tFltrFlowSpecProblem,
                tFltrFlowSpecProblemDescription,
                tFltrFLowSpecNLRI,
                tFltrFlowSpecVrtrId,
                tFltrPrefixListType,
                tFltrPrefixListName,
                tFltrApplyPathSource,
                tFltrApplyPathIndex,
                tFltrNotifDescription,
                tFltrMdaId
            }
    STATUS    current
    DESCRIPTION
         "The group of objects supporting management of filter
         notification objects on Nokia SROS series systems."
    ::= { tFilterMIBGroups 53 }

tIPFilterV13v0Group OBJECT-GROUP
    OBJECTS {
        tIPFilterParamsExtTbleLstChgd,
        tIPFilterParamsExtLastChanged,
        tIPFilterSharedPccRuleInsrtPt,
        tIPFilterSharedPccRuleInsrtSize,
        tIPFilterSharedPccRuleNbrInsrtd,
        tIPFilterChainToSystemFilter,
        tIPFilterParamsExtTTLVal1,
        tIPFilterParamsExtTTLVal2,
        tIPFilterParamsExtTTLOper,
        tIPFilterParamsExtEgressPBR,
        tIPFilterParamsExtEsi,
        tIPFilterParamsExtFwdEsiSvcId,
        tIPFilterParamsExtFwdEsiVRtrId,
        tIPFilterParamsExtFwdEsiSFIp,
        tIPFilterParamsExtPbrDwnActOvr,
        tIPFilterParamsExtFwdEsiVasIf
    }
    STATUS    current
    DESCRIPTION
         "The group of objects supporting IP Filters
         on Nokia 7x50 ESS/SR series systems 13.0 release."
    ::= { tFilterMIBGroups 54 }

tIPv6FilterV13v0Group OBJECT-GROUP
    OBJECTS {
        tIPv6FilterParamsExtPktLenVal1,
        tIPv6FilterParamsExtPktLenVal2,
        tIPv6FilterParamsExtPktLenOper,
        tIPv6FilterSharedPccRuleInsrtPt,  
        tIPv6FilterSharedPccRuleInsrtSiz, 
        tIPv6FilterSharedPccRuleNbrInsrt,
        tIPv6FilterChainToSystemFilter,
        tIPv6FilterParamsExtHopLimitVal1,
        tIPv6FilterParamsExtHopLimitVal2,
        tIPv6FilterParamsExtHopLimitOper,
        tIPv6FilterParamsExtEgressPBR,
        tIPv6FilterParamsExtEsi,
        tIPv6FilterParamsExtFwdEsiSvcId,
        tIPv6FilterParamsExtFwdEsiVRtrId,
        tIPv6FilterParamsExtFwdEsiSFIp,
        tIPv6FilterParamsExtPbrDwnActOvr,
        tIPv6FilterParamsExtFwdEsiVasIf
    }
    STATUS    current
    DESCRIPTION
         "The group of objects supporting IPv6 Filters
         on Nokia 7x50 ESS/SR series systems 13.0 release."
    ::= { tFilterMIBGroups 55 }

tFilterRPlcyV13v0ObsoleteGroup OBJECT-GROUP
    OBJECTS {
                tFilterRPActiveDest,

                tFilterRDRowStatus,
                tFilterRDDescription,
                tFilterRDAdminPriority,
                tFilterRDOperPriority,
                tFilterRDAdminState,
                tFilterRDOperState,

                tFilterRSTRowStatus,
                tFilterRSTOID,
                tFilterRSTCommunity,
                tFilterRSTSNMPVersion,
                tFilterRSTInterval,
                tFilterRSTTimeout,
                tFilterRSTDropCount,
                tFilterRSTHoldDown,
                tFilterRSTHoldDownRemain,
                tFilterRSTLastActionTime,
                tFilterRSTLastOID,
                tFilterRSTLastType,
                tFilterRSTLastCounter32Val,
                tFilterRSTLastUnsigned32Val,
                tFilterRSTLastTimeTicksVal,
                tFilterRSTLastInt32Val,
                tFilterRSTLastOctetStringVal,
                tFilterRSTLastIpAddressVal,
                tFilterRSTLastOidVal,
                tFilterRSTLastCounter64Val,
                tFilterRSTLastOpaqueVal,
                tFilterRSTLastAction,
                tFilterRSTLastPrioChange,
                tFilterRSTNextRespIndex,

                tFilterRSTRespRowStatus,
                tFilterRSTRespAction,
                tFilterRSTRespPrioChange,
                tFilterRSTRespOID,
                tFilterRSTRespType,
                tFilterRSTCounter32Val,
                tFilterRSTUnsigned32Val,
                tFilterRSTTimeTicksVal,
                tFilterRSTInt32Val,
                tFilterRSTOctetStringVal,
                tFilterRSTIpAddressVal,
                tFilterRSTOidVal,
                tFilterRSTCounter64Val,
                tFilterRSTOpaqueVal,

                tFilterRUTRowStatus,
                tFilterRUTURL,
                tFilterRUTHTTPVersion,
                tFilterRUTInterval,
                tFilterRUTTimeout,
                tFilterRUTDropCount,
                tFilterRUTHoldDown,
                tFilterRUTHoldDownRemain,
                tFilterRUTLastActionTime,
                tFilterRUTLastRetCode,
                tFilterRUTLastAction,
                tFilterRUTLastPrioChange,

                tFilterRUTRespRowStatus,
                tFilterRUTRespAction,
                tFilterRUTRespPrioChange,

                tFilterRPTRowStatus,
                tFilterRPTInterval,
                tFilterRPTTimeout,
                tFilterRPTDropCount,
                tFilterRPTHoldDown,
                tFilterRPTHoldDownRemain,
                tFilterRPTLastActionTime,
                tFilterRPTLastAction
            }
    STATUS current
    DESCRIPTION
        "The group of obsoleted objects in 13.0 supporting management of filter
        redirect policy on Nokia SROS series systems."
    ::= { tFilterMIBGroups 56 }

tFilterSystemFilterV13v0Group OBJECT-GROUP
    OBJECTS {
                tFilterSystemFilterTableLastChg,
                tFilterSystemFilterLastChanged,
                tFilterSystemFilterRowStatus
            }
    STATUS  current
    DESCRIPTION
        "The group of objects supporting system filter policies
         on Nokia 7x50 ESS/SR series systems 13.0 release."
    ::= { tFilterMIBGroups 57 }

tFilterEmbeddedInsertV13v0Group OBJECT-GROUP
    OBJECTS {
        tFilterEmbedOflowSvcContext , 
        tFilterEmbedOflowSapContextPort,
        tFilterEmbedOflowSapContextEncap,
        tFilterEmbedOflowContextType
    }
    STATUS current
    DESCRIPTION
        "The group of new objects supporting the creation of embedded filters
         for Nokia SROS systems 13.0 release."
    ::= { tFilterMIBGroups 58 }

tDhcpFilterV13v0Group OBJECT-GROUP
    OBJECTS {
        tDhcpFilterDefAction             ,
        
        tDhcp6FilterTblLastChanged       ,
        tDhcp6FilterRowStatus            ,
        tDhcp6FilterLastChanged          ,
        tDhcp6FilterDescription          ,
        tDhcp6FilterDefAction            ,

        tDhcp6FilterParamsTblLastChanged ,
        tDhcp6FilterParamsRowStatus      ,
        tDhcp6FilterParamsLastChanged    ,
        tDhcp6FilterParamsOptionNumber   ,
        tDhcp6FilterParamsOptionMatch    ,
        tDhcp6FilterParamsAction         ,
        tDhcp6FilterParamsOptionValue    ,
        tDhcp6FilterDefActionFlags       ,
        tDhcp6FilterParamsActionFlags
        }
    STATUS    current
    DESCRIPTION
        "The group of objects supporting DHCP Filters
         on Nokia 7x50 ESS/SR series systems 13.0 release."
    ::= { tFilterMIBGroups 59 }

tMacFilterV13v0Group OBJECT-GROUP
    OBJECTS {
        tMacFilterParamsEsi,
        tMacFilterParamsFwdEsiSvcId,
        tMacFilterParamsPbrDwnActOvr
    }
    STATUS    current
    DESCRIPTION
         "The group of objects supporting MAC Filters
         on Nokia 7x50 ESS/SR series systems 13.0 release."
    ::= { tFilterMIBGroups 60 }

tFilterNotificationsV14v0Group NOTIFICATION-GROUP
    NOTIFICATIONS {
            tFilterEmbedFlowspecOperStateChg,
            tFilterEmbedVsdOperStateChg
    }
    STATUS current
    DESCRIPTION
        "The group of notifications supporting management of
         filter notifications on Nokia SROS
         series systems 14.0 release."
    ::= { tFilterMIBGroups 61 }
tFilterEmbedFlowspecGroup OBJECT-GROUP
    OBJECTS {
        tFilterEmbedFlowspecTableLstChg,
        tFilterEmbedFlowspecRowStatus,
        tFilterEmbedFlowspecLastChanged,
        tFilterEmbedFlowspecRtrId,
        tFilterEmbedFlowspecAdminState,
        tFilterEmbedFlowspecOperState,
        tFltrEmbFlowSpecInfoFltrId,
        tFltrEmbFlowSpecInfoEntryCnt,
        tFltrEmbFlowSpecInfoEntryCntIns,
        tFltrEmbFlowspecEntryInsEntryId,
        tFltrEmbFlowspecEntryOperState
    }
    STATUS current
    DESCRIPTION
        "The group of objects supporting embedding of flowspec rules on
         Nokia SROS systems 14.0 release."
    ::= { tFilterMIBGroups 62 }

tFilterIPvXRedundantActionGroup OBJECT-GROUP
    OBJECTS {
        tIPvXFltrEntryActionTblLChg,
        tIPvXFltrEntryActRowStatus,
        tIPvXFltrEntryActLastChanged,
        tIPvXFltrEntryActAction,
        tIPvXFltrEntryActFwdNHIpAddrType,
        tIPvXFltrEntryActFwdNHIpAddr,
        tIPvXFltrEntryActFwdNHIndirect,
        tIPvXFltrEntryActFwdNHInterface,
        tIPvXFltrEntryActFwdRedPlcy,
        tIPvXFltrEntryActFwdSapPortId,
        tIPvXFltrEntryActFwdSapEncapVal,
        tIPvXFltrEntryActFwdSdpBind,
        tIPvXFltrEntryActRedirectURL,
        tIPvXFltrEntryActRdirAllwRadOvr,
        tIPvXFltrEntryActFwdRtrId,
        tIPvXFltrEntryActNatPolicyName,
        tIPvXFltrEntryActNatType,
        tIPvXFltrEntryActFwdLsp,
        tIPvXFltrEntryActFwdLspRtrId,
        tIPvXFltrEntryActPktLenVal1,
        tIPvXFltrEntryActPktLenVal2,
        tIPvXFltrEntryActPktLenOper,
        tIPvXFltrEntryActTTLVal1,
        tIPvXFltrEntryActTTLVal2,
        tIPvXFltrEntryActTTLOper,
        tIPvXFltrEntryActEsi,
        tIPvXFltrEntryActFwdEsiSvcId,
        tIPvXFltrEntryActFwdEsiVRtrId,
        tIPvXFltrEntryActFwdEsiSFIpType,
        tIPvXFltrEntryActFwdEsiSFIp,
        tIPvXFltrEntryActFwdEsiVasIf,
        tIPFilterParamsExtStickyDst,
        tIPFilterParamsExtDownloadAct,
        tIPFilterParamsExtHoldRemain,
        tIPv6FilterParamsExtStickyDst,
        tIPv6FilterParamsExtDownloadAct,
        tIPv6FilterParamsExtHoldRemain,
        tIPvXFltrEntryActPbrTargetStatus,
        tIPvXFltrEntryActRateLimit
   }
    STATUS    current
    DESCRIPTION
         "The group of objects supporting redundant ip filter
         actions on Nokia 7x50 ESS/SR series systems 14.0 release."
    ::= { tFilterMIBGroups 63 }

tFilterMacRedundantActionGroup OBJECT-GROUP
    OBJECTS {
        tMacFltrEntryActionTblLChg,
        tMacFltrEntryActRowStatus,
        tMacFltrEntryActLastChanged,
        tMacFltrEntryActAction,
        tMacFltrEntryActRowStatus,
        tMacFltrEntryActFwdSapPortId,
        tMacFltrEntryActFwdSapEncapVal,
        tMacFltrEntryActFwdSdpBind,
        tMacFltrEntryActRedirectURL,
        tMacFltrEntryActEsi,
        tMacFltrEntryActFwdEsiSvcId,
        tMacFilterParamsStickyDst,
        tMacFilterParamsHoldRemain,
        tMacFilterParamsDownloadAct,
        tMacFltrEntryActPbrTargetStatus,
        tMacFltrEntryActRateLimit
  }
    STATUS    current
    DESCRIPTION
         "The group of objects supporting redundant mac filter
         actions on Nokia 7x50 ESS/SR series systems 14.0 release."
    ::= { tFilterMIBGroups 64 }

tFilterEmbedVsdGroup OBJECT-GROUP
    OBJECTS {
        tFilterEmbedVsdTableLstChg,
        tFilterEmbedVsdRowStatus,
        tFilterEmbedVsdLastChanged,
        tFilterEmbedVsdAdminState,
        tFilterEmbedVsdOperState,
        tFltrEmbedVsdInfoEntryCnt,
        tFltrEmbedVsdInfoEntryCntInsrtd,
        tFilterEmbedVsdEntryInsrtEntryId,
        tFilterEmbedVsdEntryOperState
    }
    STATUS current
    DESCRIPTION
         "The group of objects supporting embedding of filters managed
          by a VSD controller on Nokia 7x50 ESS/SR series systems
          14.0 release."
    ::= { tFilterMIBGroups 65 }

tFilterEmbeddedRefGroup OBJECT-GROUP
    OBJECTS {
        tFilterEmbeddedRefLastChanged
    }
    STATUS current
    DESCRIPTION
         "The group of objects extending support of embedding of filters
          Nokia 7x50 ESS/SR series systems 14.0 release."
    ::= { tFilterMIBGroups 66 }

tFilterTimeRangeObsoletedGroup OBJECT-GROUP
    OBJECTS {
        tIPFilterParamsTimeRangeName,
        tIPFilterParamsTimeRangeState,
        tMacFilterParamsTimeRangeName,
        tMacFilterParamsTimeRangeState,
        tIPv6FilterParamsTimeRangeName,
        tIPv6FilterParamsTimeRangeState
    }
    STATUS current
    DESCRIPTION
        "The group of obsoleted objects in 14.0 supporting Time Of Day / Time
         Range features on Nokia SROS series systems."
    ::= { tFilterMIBGroups 67 }

tFilterObsoletedNotifsGroup NOTIFICATION-GROUP
    NOTIFICATIONS {
        tFilterEntryActivationFailed,
        tFilterEntryActivationRestored
    }
    STATUS current
    DESCRIPTION
        "The group of obsoleted notifications for filter features
         on Nokia SROS series systems."
    ::= { tFilterMIBGroups 68 }

tFilterEntryStatGroup OBJECT-GROUP
    OBJECTS {
        tFltrEntryStatIngHitCnt,
        tFltrEntryStatEgrHitCnt,
        tFltrEntryStatIngHitCntB,
        tFltrEntryStatEgrHitCntB,
        tFltrEntryStatRateLmtIngHitCnt,
        tFltrEntryStatRateLmtIngDrop,
        tFltrEntryStatRateLmtIngFwd,
        tFltrEntryStatRateLmtIngHitCntB,
        tFltrEntryStatRateLmtIngDropB,
        tFltrEntryStatRateLmtIngFwdB,
        tFltrEntryStatRateLmtEgrHitCnt,
        tFltrEntryStatRateLmtEgrDrop,
        tFltrEntryStatRateLmtEgrFwd,
        tFltrEntryStatRateLmtEgrHitCntB,
        tFltrEntryStatRateLmtEgrDropB,
        tFltrEntryStatRateLmtEgrFwdB
    }
    STATUS current
    DESCRIPTION
         "The group of objects supporting filter
         action rate-limit on Nokia 7x50 ESS/SR series systems 14.0 release."
    ::= { tFilterMIBGroups 69 }

tFilterRemarkDscpGroup OBJECT-GROUP
    OBJECTS {
        tIPvXFltrEntryActRemarkDSCP
    }
    STATUS current
    DESCRIPTION
         "The group of objects supporting filter remark dscp action on Nokia
          7x50 ESS/SR series systems 14.0 release."
    ::= { tFilterMIBGroups 70 }

tIPFilterV14v0Group OBJECT-GROUP
    OBJECTS {
                tIPFilterRowStatus,
                tIPFilterScope,
                tIPFilterDescription,
                tIPFilterDefaultAction,
                tIPFilterRadiusInsertPt,
                tIPFilterRadiusInsertSize,
                tIPFilterCreditCntrlInsertPt,
                tIPFilterCreditCntrlInsertSize,
                tIPFilterSubInsertHighWmark,
                tIPFilterSubInsertLowWmark,
                tIpFilterCreditCntrlNbrInsertd,
                tIpFilterRadiusNbrInsertd,
                tIPFilterHostSharedInsertPt,
                tIPFilterHostSharedInsertSize,
                tIpFilterHostSharedNbrInsertd,
                tIPFilterHostSharedHighWmark,
                tIPFilterHostSharedLowWmark,
                tIPFilterNbrHostSharedFltrs,
                tIPFilterParamsRowStatus,
                tIPFilterParamsLogId,
                tIPFilterParamsDescription,
                tIPFilterParamsAction,
                tIPFilterParamsForwardNH,
                tIPFilterParamsForwardNHIndirect,
                tIPFilterParamsSourceIpAddr,
                tIPFilterParamsSourceIpMask,
                tIPFilterParamsDestinationIpAddr,
                tIPFilterParamsDestinationIpMask,
                tIPFilterParamsProtocol,
                tIPFilterParamsSourcePortValue1,
                tIPFilterParamsSourcePortValue2,
                tIPFilterParamsSourcePortOperator,
                tIPFilterParamsDestPortValue1,
                tIPFilterParamsDestPortValue2,
                tIPFilterParamsDestPortOperator,
                tIPFilterParamsDSCP,
                tIPFilterParamsFragment,
                tIPFilterParamsOptionPresent,
                tIPFilterParamsIpOptionValue,
                tIPFilterParamsIpOptionMask,
                tIPFilterParamsMultipleOption,
                tIPFilterParamsTcpSyn,
                tIPFilterParamsTcpAck,
                tIPFilterParamsIcmpCode,
                tIPFilterParamsIcmpType,
                tIPFilterParamsCflowdSample,
                tIPFilterParamsCflowdIfSample,
                tIPFilterParamsForwardNHInterface,
                tIPFilterParamsIngressHitCount,
                tIPFilterParamsEgressHitCount,
                tIPFilterParamsLogInstantiated,
                tIPFilterParamsForwardRedPlcy,
                tIPFilterParamsActiveDest,
                tIPFilterParamsFwdSvcId,
                tIPFilterParamsFwdSapPortId,
                tIPFilterParamsFwdSapEncapVal,
                tIPFilterParamsFwdSdpBind,
                tIPFilterParamsRedirectURL,
                tIPFilterParamsSrcIpFullMask,
                tIPFilterParamsDestIpFullMask,
                tIPFilterParamsIngrHitByteCount,
                tIPFilterParamsEgrHitByteCount,
                tFltrGrpInsrtdEntriesFilterType,
                tFltrGrpInsrtdEntriesFilterId,
                tFltrGrpInsrtdEntriesApplication,
                tFltrGrpInsrtdEntriesLocation,
                tFltrGrpInsrtdEntriesResult,
                tFltrGrpInsrtdEntriesFeedback,
                tFltrGrpInsrtdEntriesExecute,
                tIPFilterParamsFwdRtrId,
                tIPFilterParamsSrcRouteOption,
                tIPFilterParamsPortSelector,
                tIPFilterParamsSrcPortList,
                tIPFilterParamsDstPortList,
                tIPFilterParamsExtTbleLstChgd,
                tIPFilterParamsExtLastChanged,
                tIPFilterParamsExtPktLenVal1,
                tIPFilterParamsExtPktLenVal2,
                tIPFilterParamsExtPktLenOper,
                tIPFilterParamsRdirAllwRadOvrd,
                tIPFilterParamsNatPolicyName,
                tIPFilterParamsFwdLsp,
                tIPFilterParamsFwdLspRtrId
            }
    STATUS    current
    DESCRIPTION
        "The group of objects supporting IP Filters
         on Nokia 7x50 ESS/SR series systems 14.0 release."
    ::= { tFilterMIBGroups 71 }

tIPv6FilterV14v0Group OBJECT-GROUP
    OBJECTS {
        tIPv6FilterRowStatus,
        tIPv6FilterScope,
        tIPv6FilterDescription,
        tIPv6FilterDefaultAction,
        tIPv6FilterRadiusInsertPt,
        tIPv6FilterRadiusInsertSize,
        tIPv6FilterCreditCntrlInsertPt,
        tIPv6FilterCreditCntrlInsertSize,
        tIPv6FilterSubInsertHighWmark,
        tIPv6FilterSubInsertLowWmark,
        tIpv6FilterCreditCntrlNbrInsertd,
        tIpv6FilterRadiusNbrInsertd,
        tIPv6FilterHostSharedInsertPt,
        tIPv6FilterHostSharedInsertSize,
        tIpv6FilterHostSharedNbrInsertd,
        tIPv6FilterHostSharedHighWmark,
        tIPv6FilterHostSharedLowWmark,
        tIPv6FilterNbrHostSharedFltrs,
        tIPv6FilterParamsRowStatus,
        tIPv6FilterParamsLogId,
        tIPv6FilterParamsDescription,
        tIPv6FilterParamsAction,
        tIPv6FilterParamsForwardNH,
        tIPv6FilterParamsForwardNHIndirect,
        tIPv6FilterParamsSourceIpAddr,
        tIPv6FilterParamsSourceIpMask,
        tIPv6FilterParamsDestinationIpAddr,
        tIPv6FilterParamsDestinationIpMask,
        tIPv6FilterParamsNextHeader,
        tIPv6FilterParamsSourcePortValue1,
        tIPv6FilterParamsSourcePortValue2,
        tIPv6FilterParamsSourcePortOperator,
        tIPv6FilterParamsDestPortValue1,
        tIPv6FilterParamsDestPortValue2,
        tIPv6FilterParamsDestPortOperator,
        tIPv6FilterParamsDSCP,
        tIPv6FilterParamsTcpSyn,
        tIPv6FilterParamsTcpAck,
        tIPv6FilterParamsIcmpCode,
        tIPv6FilterParamsIcmpType,
        tIPv6FilterParamsCflowdSample,
        tIPv6FilterParamsCflowdIfSample,
        tIPv6FilterParamsForwardNHInterface,
        tIPv6FilterParamsIngressHitCount,
        tIPv6FilterParamsEgressHitCount,
        tIPv6FilterParamsLogInstantiated,
        tIPv6FilterParamsForwardRedPlcy,
        tIPv6FilterParamsActiveDest,
        tIPv6FilterParamsIngrHitByteCount,
        tIPv6FilterParamsEgrHitByteCount,
        tIPv6FilterParamsFwdSvcId,
        tIPv6FilterParamsFwdSapPortId,
        tIPv6FilterParamsFwdSapEncapVal,
        tIPv6FilterParamsFwdSdpBind,
        tIPv6FilterParamsRedirectURL,
        tIPv6FilterParamsSrcIpPrefixList,
        tIPv6FilterParamsDstIpPrefixList,
        tIPv6FilterParamsFragment,
        tIPv6FilterParamsHopByHopOpt,
        tIPv6FilterParamsRoutingType0,
        tIPv6FilterParamsPortSelector,
        tIPv6FilterParamsSrcPortList,
        tIPv6FilterParamsDstPortList,
        tIPv6FilterParamsRdirAllwRadOvrd,
        tIPv6FilterParamsFwdRtrId,
        tIPv6FilterParamsSrcIpFullMask,
        tIPv6FilterParamsDstIpFullMask,
        tIPv6FilterParamsNatPolicyName,
        tIPv6FilterParamsFlowLabel,
        tIPv6FilterParamsFlowLabelMask,
        tIPv6FilterParamsFwdLspRtrId,
        tIPv6FilterParamsFwdLsp,
        tIPv6FilterParamsExtTbleLstChgd,
        tIPv6FilterParamsExtLastChanged,
        tIPv6FilterParamsExtAhExtHdr,
        tIPv6FilterParamsExtEspExtHdr,
        tIPv6FilterParamsExtNatType
    }
    STATUS    current
    DESCRIPTION
        "The group of objects supporting management of IPv6 filter objects
         on Nokia 7x50 ESS/SR series systems 14.0 release."
    ::= { tFilterMIBGroups 72 }

tFilterParamsObsoletedGroup OBJECT-GROUP
    OBJECTS {
        tIPFilterParamsRemarkDSCP,
        tIPFilterParamsRemarkDSCPMask,
        tIPFilterParamsRemarkDot1p,
        tIPv6FilterParamsRemarkDSCP,
        tIPv6FilterParamsRemarkDSCPMask,
        tIPv6FilterParamsRemarkDot1p
    }
    STATUS    current
    DESCRIPTION
        "The group of objects supporting management of IP/IPv6 filter
         on Nokia 7x50 ESS/SR series systems which were obsoleted
         in 14.0 release."
    ::= { tFilterMIBGroups 73 }

tFilterRemarkDscpExtGroup OBJECT-GROUP
    OBJECTS {
        tIPvXFltrEntryActActionExt
    }
    STATUS current
    DESCRIPTION
         "The group of objects supporting filter remark dscp extended action on
          Nokia 7x50 ESS/SR series systems 14.0 release."
    ::= { tFilterMIBGroups 74 }

tFilterPrefListInfoGroup OBJECT-GROUP
    OBJECTS {
        tFltrPrefListInfoPrefixOwner
    }
    STATUS current
    DESCRIPTION
         "The group of objects supporting prefix list info table
          context on Nokia 7x50 ESS/SR series systems."
    ::= { tFilterMIBGroups 76 }
END

TIMETRA-CALLTRACE-MIB DEFINITIONS ::= BEGIN

IMPORTS
    MODULE-IDENTITY, OBJECT-TYPE,
    NOTIFICATION-TYPE, Unsigned32, Integer32, Counter32, Gauge32, IpAddress
        FROM SNMPv2-SMI

    MODULE-COMPLIANCE, OBJECT-GROUP, NOTIFICATION-GROUP
        FROM SNMPv2-CONF

    TEXTUAL-CONVENTION, RowStatus, TruthValue, TimeStamp, MacAddress,
    DateAndTime, DisplayString
        FROM SNMPv2-TC

    timetraSRMIBModules, tmnxSRObjs, tmnxSRNotifyPrefix, tmnxSRConfs
        FROM TIMETRA-GLOBAL-MIB

    TNamedItem, TNamedItemOrEmpty, TItemDescription, TmnxVRtrID, TmnxPortID,
    TmnxEncapVal
        FROM TIMETRA-TC-MIB

    InetAddressType, InetAddress, InetPortNumber
        FROM INET-ADDRESS-MIB

    TmnxSlotNum
        FROM TIMETRA-CHASSIS-MIB

    ;

timetraCallTraceMIBModule  MODULE-IDENTITY
        LAST-UPDATED "201601010000Z"
        ORGANIZATION "Nokia"
        CONTACT-INFO
            "Nokia SROS Support
             Web: http://www.nokia.com"
        DESCRIPTION

        "This document is the SNMP MIB module for the Nokia SROS
        implementation of Call Trace.

        Copyright 2003-2016 Nokia. All rights reserved.
        Reproduction of this document is authorized on the condition that
        the foregoing copyright notice is included.

        This SNMP MIB module (Specification) embodies Nokia's
        proprietary intellectual property.  Nokia retains all
        title and ownership in the Specification, including any
        revisions.

        Nokia grants all interested parties a non-exclusive
        license to use and distribute an unmodified copy of this
        Specification in connection with management of Nokia products,
        and without fee, provided this copyright notice and license
        appear on all copies.

        This Specification is supplied `as is', and Nokia makes
        no warranty, either express or implied, as to the use,
        operation, condition, or performance of the Specification."

        REVISION        "201601010000Z"
        DESCRIPTION     "Rev 14.0               01 Jan 2016 00:00
                         14.0 release of the TIMETRA-CALLTRACE-MIB."

        REVISION        "201502010000Z"
        DESCRIPTION     "Rev 13.0              1 Feb 2015 00:00
                         Initial version of the TIMETRA-CALLTRACE-MIB."

        REVISION        "201502010000Z"
        DESCRIPTION     "Rev 0.1               1 Feb 2015 00:00
                         Initial version of the TIMETRA-CALLTRACE-MIB."

        ::= { timetraSRMIBModules 102 }


-- =========================================================================
-- Nokia 7xxx series Call Trace MIB structure
-- ==========================================================================
tmnxCallTraceObjs            OBJECT IDENTIFIER ::= { tmnxSRObjs         102 }
tmnxCallTraceConformance     OBJECT IDENTIFIER ::= { tmnxSRConfs        102 }
  tmnxCallTraceCompliances   OBJECT IDENTIFIER ::= { tmnxCallTraceConformance  1 }
  tmnxCallTraceGroups        OBJECT IDENTIFIER ::= { tmnxCallTraceConformance  2 }
tmnxCallTraceNotifyPrefix    OBJECT IDENTIFIER ::= { tmnxSRNotifyPrefix 102 }
  tmnxCallTraceNotifications OBJECT IDENTIFIER ::= { tmnxCallTraceNotifyPrefix 0 }

-- ==========================================================================
-- Textual conventions
-- ==========================================================================
TmnxCallTraceSizeLimit ::= TEXTUAL-CONVENTION
    STATUS current
    DESCRIPTION
        "The TmnxCallTraceSizeLimit textual convention is used to specify
         the data volume limit for a call trace job."
    SYNTAX Unsigned32 (1..1000)

TmnxCallTraceTimeLimit ::= TEXTUAL-CONVENTION
    STATUS current
    DESCRIPTION
        "The TmnxCallTraceTimeLimit textual convention is used to specify
         the time limit for a call trace job."
    SYNTAX Unsigned32 (1..604800)

TmnxCallTraceJobStatus ::= TEXTUAL-CONVENTION
    STATUS current
    DESCRIPTION
        "The TmnxCallTraceJobStatus textual convention is used to specify
         the status of a call trace job.

         The value 'running (0)' indicates the job is active and is tracing
         events triggered by the host being monitored.

         The value 'finished (1)' indicates the job has already finished
         and is not tracing events generated by the host anymore."
    SYNTAX INTEGER {
                     running (0),
                     finished (1)
                   }

TmnxCallTraceCFlashId ::= TEXTUAL-CONVENTION
    STATUS current
    DESCRIPTION
        "The TmnxCallTraceCFlashId textual convention is used to specify
         the ID of a compact flash (cflash) card."
    SYNTAX INTEGER {
                     cf1 (1),
                     cf2 (2)
                   }


TmnxCallTraceHostType ::= TEXTUAL-CONVENTION
    STATUS current
    DESCRIPTION
        "The TmnxCallTraceHostType textual convention is used to specify
         the type of the host to trace."
    SYNTAX      INTEGER {
                          ue(1)
                        }
-- ==========================================================================
-- SCALARS
-- ==========================================================================
tmnxCallTraceScalarObjs      OBJECT IDENTIFIER ::= { tmnxCallTraceObjs 1 }

-- --------------------------------------------------------------------------
-- Objects indicating last changes to call trace configuration tables
-- --------------------------------------------------------------------------
tmnxCallTraceLastChangedObjs   OBJECT IDENTIFIER ::= { tmnxCallTraceScalarObjs 1 }

tmnxCallTraceProfileTblLstChgd OBJECT-TYPE
    SYNTAX      TimeStamp
    MAX-ACCESS  read-only
    STATUS      current
    DESCRIPTION
        "The value of the object tmnxCallTraceProfileTblLstChgd indicates
         the sysUpTime at the time of the last modification
         to tmnxCallTraceProfileTable by adding, deleting an entry or change
         to a writable object in the table.

         If no changes were made to the table since the last re-initialization
         of the local network management subsystem, then this object contains
         a zero value."
    ::= { tmnxCallTraceLastChangedObjs 1 }

tmnxCallTraceLocationTblLstChgd OBJECT-TYPE
    SYNTAX      TimeStamp
    MAX-ACCESS  read-only
    STATUS      current
    DESCRIPTION
        "The value of the object tmnxCallTraceLocationTblLstChgd indicates
         the sysUpTime at the time of the last modification
         to tmnxCallTraceLocationTable by adding, deleting an entry or change
         to a writable object in the table.

         If no changes were made to the table since the last re-initialization
         of the local network management subsystem, then this object contains
         a zero value."
    ::= { tmnxCallTraceLastChangedObjs 2 }

-- --------------------------------------------------------------------------
-- Call trace configuration related scalar objects
-- --------------------------------------------------------------------------
tmnxCallTraceScalarConfigObjs  OBJECT IDENTIFIER ::= { tmnxCallTraceScalarObjs 2 }

tmnxCallTraceMaxFilesNumber  OBJECT-TYPE
    SYNTAX      Unsigned32 (1..1024)
    MAX-ACCESS  read-write
    STATUS      current
    DESCRIPTION
        "The value of the object tmnxCallTraceMaxFilesNumber specifies
         the maximum number of all call trace log files stored on all compact
         flash cards together.

         The value comprises both active and finished jobs."
    DEFVAL { 200 }
    ::= { tmnxCallTraceScalarConfigObjs 1 }

tmnxCallTracePrimaryCFlash  OBJECT-TYPE
    SYNTAX      TmnxCallTraceCFlashId
    MAX-ACCESS  read-write
    STATUS      current
    DESCRIPTION
        "The value of the object tmnxCallTracePrimaryCFlash specifies
         the compact flash card to be used as the primary local storage location
         to save the generated call trace log files.

         The system will write to the specified compact flash card until
         the size of all generated files reaches the limit defined by the value
         of the object tmnxCallTraceLocationSizeLimit for the given compact
         flash card and the card is not disabled as the local storage location
         by the value of the object tmnxCallTraceLocationDisable.

         Once the limit is reached or the card is disabled the files
         will be written to the other compact flash card.

         The compact flash card must be available in the system in order to
         select it as the primary storage location. If the card is not
         available at the moment of SNMP SET operation, the other card is
         automatically selected as the primary location."
    DEFVAL { cf1 }
    ::= { tmnxCallTraceScalarConfigObjs 2 }

tmnxCallTraceScalarStatsObjs OBJECT IDENTIFIER ::= { tmnxCallTraceScalarObjs 3 }

tmnxCallTraceUsedFilesNumber  OBJECT-TYPE
    SYNTAX      Unsigned32 (0..1024)
    MAX-ACCESS  read-only
    STATUS      current
    DESCRIPTION
        "The value of the object tmnxCallTraceUsedFilesNumber indicates
         the number of all call trace log files stored on all compact
         flash cards together.

         The value comprises both active and finished jobs."
    ::= { tmnxCallTraceScalarStatsObjs 1 }

tmnxCallTraceAvailFilesNumber  OBJECT-TYPE
    SYNTAX      Unsigned32 (0..1024)
    MAX-ACCESS  read-only
    STATUS      current
    DESCRIPTION
        "The value of the object tmnxCallTraceAvailFilesNumber indicates
         the remaining number of call trace log files available for use
         on all compact flash cards together.

         The value comprises both active and finished jobs."
    ::= { tmnxCallTraceScalarStatsObjs 2 }

-- ==========================================================================
-- TABLES
-- =========================================================================
tmnxCallTraceConfigObjs  OBJECT IDENTIFIER ::= { tmnxCallTraceObjs 2 }

-- --------------------------------------------------------------------------
-- Call trace profile related objects
-- --------------------------------------------------------------------------
tmnxCallTraceProfileTable  OBJECT-TYPE
    SYNTAX      SEQUENCE OF TmnxCallTraceProfileEntry
    MAX-ACCESS  not-accessible
    STATUS      current
    DESCRIPTION
        "The table tmnxCallTraceProfileTable contains information pertaining to
         call trace profiles configured on the system.

         A call trace profile is a collection of parameters used for creation
         of call trace jobs.

         A maximum of 10 profiles can be configured in the system."
    ::= { tmnxCallTraceConfigObjs 1 }

tmnxCallTraceProfileEntry  OBJECT-TYPE
    SYNTAX      TmnxCallTraceProfileEntry
    MAX-ACCESS  not-accessible
    STATUS      current
    DESCRIPTION
        "Each row entry represents a call trace profile defined in the system.

         Rows in the table tmnxCallTraceProfileTable are created and destroyed
         by SNMP SET operations on the object tmnxCallTraceProfileRowStatus.

         The call trace profile 'default' is created by the agent itself
         at the initialization of the system and cannot be modified or deleted
         by SNMP SET operations."
    INDEX { IMPLIED tmnxCallTraceProfileName }
    ::= { tmnxCallTraceProfileTable 1 }

TmnxCallTraceProfileEntry ::= SEQUENCE {
        tmnxCallTraceProfileName         TNamedItem,
        tmnxCallTraceProfileLstChgd      TimeStamp,
        tmnxCallTraceProfileRowStatus    RowStatus,
        tmnxCallTraceProfileDescription  TItemDescription,
        tmnxCallTraceProfileSizeLimit    TmnxCallTraceSizeLimit,
        tmnxCallTraceProfileTimeLimit    TmnxCallTraceTimeLimit,
        tmnxCallTraceProfileDstAddrType  InetAddressType,
        tmnxCallTraceProfileDstAddr      InetAddress,
        tmnxCallTraceProfileDstPort      InetPortNumber,
        tmnxCallTraceProfileVRtrId       TmnxVRtrID,
        tmnxCallTraceProfileDbgOutput   TruthValue
    }

tmnxCallTraceProfileName OBJECT-TYPE
    SYNTAX      TNamedItem
    MAX-ACCESS  not-accessible
    STATUS      current
    DESCRIPTION
        "The value of the object tmnxCallTraceProfileName specifies
         the unique name of the call trace profile.

         The value 'default' is reserved for the default profile that is
         automatically created by the agent at the initialization
         of the system."
    ::= { tmnxCallTraceProfileEntry 1 }

tmnxCallTraceProfileLstChgd OBJECT-TYPE
    SYNTAX      TimeStamp
    MAX-ACCESS  read-only
    STATUS      current
    DESCRIPTION
        "The value of the object tmnxCallTraceProfileLstChgd indicates
         the sysUpTime at the time of creation or the last modification
         to this row in tmnxCallTraceProfileTable."
    ::= { tmnxCallTraceProfileEntry 2 }

tmnxCallTraceProfileRowStatus OBJECT-TYPE
    SYNTAX      RowStatus
    MAX-ACCESS  read-create
    STATUS      current
    DESCRIPTION
        "The value of the object tmnxCallTraceProfileRowStatus specifies
         the status of the conceptual row in tmnxCallTraceProfileTable.

         Rows are created and destroyed by SNMP SET operations on this
         object.

         The row corresponding to the default profile (the value of the object
         tmnxCallTraceProfileName equal to 'default') cannot be modified or
         deleted by SNMP SET operations on this object.

         Only values 'active(1)', 'createAndGo(4)' and 'destroy(6)'
         are supported."
    ::= { tmnxCallTraceProfileEntry 3 }

tmnxCallTraceProfileDescription OBJECT-TYPE
    SYNTAX      TItemDescription
    MAX-ACCESS  read-create
    STATUS      current
    DESCRIPTION
        "The value of the object tmnxCallTraceProfileDescription specifies
         the description string for this call trace profile."
    DEFVAL { ''H }
    ::= { tmnxCallTraceProfileEntry 4 }

tmnxCallTraceProfileSizeLimit OBJECT-TYPE
    SYNTAX      TmnxCallTraceSizeLimit
    UNITS       "megabytes"
    MAX-ACCESS  read-create
    STATUS      current
    DESCRIPTION
        "The value of the object tmnxCallTraceProfileSizeLimit specifies
         the maximum data volume generated by a single call trace job
         to the output in megabytes.

         After reaching the limit the call trace job for a given host
         is automatically terminated."
    DEFVAL { 10 }
    ::= { tmnxCallTraceProfileEntry 5 }

tmnxCallTraceProfileTimeLimit OBJECT-TYPE
    SYNTAX      TmnxCallTraceTimeLimit
    UNITS       "sec"
    MAX-ACCESS  read-create
    STATUS      current
    DESCRIPTION
        "The value of the object tmnxCallTraceProfileTimeLimit specifies
         the maximum duration of a single call trace job in seconds.

         After reaching the limit the call trace job for a given host
         is automatically terminated."
    DEFVAL { 86400 }
    ::= { tmnxCallTraceProfileEntry 6 }

tmnxCallTraceProfileDstAddrType OBJECT-TYPE
    SYNTAX      InetAddressType
    MAX-ACCESS  read-create
    STATUS      current
    DESCRIPTION
        "The value of the object tmnxCallTraceProfileDstAddrType specifies
         the context (IP address type or Fully Qualified Domain Name (FQDN))
         in which the value of the object tmnxCallTraceProfileDstAddr
         is to be interpreted.

         Only values 'unknown (0)', 'ipv4 (1)', 'ipv6 (2)' and 'dns (16)'
         are supported."
    DEFVAL { unknown }
    ::= { tmnxCallTraceProfileEntry 7 }

tmnxCallTraceProfileDstAddr OBJECT-TYPE
    SYNTAX      InetAddress (SIZE (0..255))
    MAX-ACCESS  read-create
    STATUS      current
    DESCRIPTION
        "The value of the object tmnxCallTraceProfileDstAddr specifies
         the live output destination address of the trace log generated
         by a call trace job.

         The value of the object can be set to a non-default value only
         if the value of the object tmnxCallTraceProfileDstAddrType
         is set to a non-default value.

         If the value is equal to default then a local compact flash card
         is used as a destination. Parameters of the local storage can
         be set in tmnxCallTraceLocationTable.

         If the value is not equal to default then the live output is being
         sent to the destination identified by the IP address / FQDN value
         of this object and the values of the objects
         tmnxCallTraceProfileDstPort and tmnxCallTraceProfileVRtrId.

         If the value of the object tmnxCallTraceProfileDstAddrType is
         'unknown (0)' then the size of this object can be only 0.

         If the value of the object tmnxCallTraceProfileDstAddrType is
         'ipv4(1)' then the size of this object can be only 4
         and the value cannot consist of all 0s.

         If the value of the object tmnxCallTraceProfileDstAddrType is
         'ipv6(2)' then the size of this object can be only 16
         and the value cannot consist of all 0s.

         If the value of the object tmnxCallTraceProfileDstAddrType is
         'dns(16)' then the size of this object can be 1..255.

         The value of this object is automatically set to default when
         the value of the object tmnxCallTraceProfileDstAddrType
         is set to 'unknown (0)'."
    DEFVAL { ''H }
    ::= { tmnxCallTraceProfileEntry 8 }

tmnxCallTraceProfileDstPort  OBJECT-TYPE
    SYNTAX      InetPortNumber (1..65535)
    MAX-ACCESS  read-create
    STATUS      current
    DESCRIPTION
        "The value of the object tmnxCallTraceProfileDstPort specifies
         the destination port for the call trace live output destination
         defined by the value of the object tmnxCallTraceProfileDstAddr.

         The value of this object is ignored if the value of the object
         tmnxCallTraceProfileDstAddr is equal to its default.

         The value of this object can be set to a non-default value only
         if the value of the object tmnxCallTraceProfileDstAddrType
         is set to a non-default value."
    DEFVAL { 29770 }
    ::= { tmnxCallTraceProfileEntry 9 }

tmnxCallTraceProfileVRtrId   OBJECT-TYPE
    SYNTAX      TmnxVRtrID
    MAX-ACCESS  read-create
    STATUS      current
    DESCRIPTION
        "The value of the object tmnxCallTraceProfileVRtrId specifies
         the virtual router instance ID in scope of which the live output
         destination identified by the values of the objects
         tmnxCallTraceProfileDstAddr and tmnxCallTraceProfileDstPort
         is to be reached.

         The default value of '1' identifies the 'Base' router instance.

         The value of this object can be set to a non-default value only
         if the value of the object tmnxCallTraceProfileDstAddrType
         is set to a non-default value."
    DEFVAL { 1 }
    ::= { tmnxCallTraceProfileEntry 10 }


tmnxCallTraceProfileDbgOutput OBJECT-TYPE
    SYNTAX      TruthValue
    MAX-ACCESS  read-create
    STATUS      current
    DESCRIPTION
       "The value of the object tmnxCallTraceProfileDbgOutput specifies
        whether the trace log generated by a call trace job will be decoded
        as text and send to debug logging.

        Enabling this object disables logging to compact flash and is
        mutually exclusive with the live-output."
    DEFVAL { false }
    ::= { tmnxCallTraceProfileEntry 12 }


-- --------------------------------------------------------------------------
-- Call trace local storage configuration related objects
-- --------------------------------------------------------------------------
tmnxCallTraceLocationTable OBJECT-TYPE
    SYNTAX      SEQUENCE OF TmnxCallTraceLocationEntry
    MAX-ACCESS  not-accessible
    STATUS      current
    DESCRIPTION
        "The table tmnxCallTraceLocationTable contains information
         pertaining to the configuration of the local storage of call trace
         log files on the compact flash cards.

         In release 14.0 only cf1 and cf2 can be used as the local
         storage of call trace log files."
    ::= { tmnxCallTraceConfigObjs 2 }

tmnxCallTraceLocationEntry  OBJECT-TYPE
    SYNTAX      TmnxCallTraceLocationEntry
    MAX-ACCESS  not-accessible
    STATUS      current
    DESCRIPTION
        "Each row entry represents one compact flash card to be used for local
         storage of call trace log files.

         Rows in the table tmnxCallTraceLocationTable are created
         by the SYSTEM at its startup and are never destroyed."
    INDEX { tmnxCallTraceLocationCFlashId }
    ::= { tmnxCallTraceLocationTable 1 }

TmnxCallTraceLocationEntry ::= SEQUENCE {
        tmnxCallTraceLocationCFlashId  Unsigned32,
        tmnxCallTraceLocationLstChgd   TimeStamp,
        tmnxCallTraceLocationSizeLimit Unsigned32,
        tmnxCallTraceLocationDisable   TruthValue
    }

tmnxCallTraceLocationCFlashId OBJECT-TYPE
    SYNTAX      Unsigned32 (1|2)
    MAX-ACCESS  not-accessible
    STATUS      current
    DESCRIPTION
        "The value of the object tmnxCallTraceLocationCFlashId specifies
         the ID of the compact flash card.

         In release 14.0 only cf1 and cf2 can be used as the local
         storage of call trace log files."
    ::= { tmnxCallTraceLocationEntry 1 }

tmnxCallTraceLocationLstChgd OBJECT-TYPE
    SYNTAX      TimeStamp
    MAX-ACCESS  read-only
    STATUS      current
    DESCRIPTION
        "The value of the object tmnxCallTraceLocationLstChgd indicates
         the sysUpTime at the time of creation or the last modification
         to this row in tmnxCallTraceLocationTable."
    ::= { tmnxCallTraceLocationEntry 2 }

tmnxCallTraceLocationSizeLimit OBJECT-TYPE
    SYNTAX      Unsigned32 (0..65536)
    UNITS       "megabytes"
    MAX-ACCESS  read-write
    STATUS      current
    DESCRIPTION
        "The value of the object tmnxCallTraceLocationSizeLimit specifies
         the maximum cumulative size of all local call trace log files stored
         on the given compact flash card.

         The value '0' means there is no size limit defined."
    DEFVAL { 1000 }
    ::= { tmnxCallTraceLocationEntry 3 }

tmnxCallTraceLocationDisable OBJECT-TYPE
    SYNTAX      TruthValue
    MAX-ACCESS  read-write
    STATUS      current
    DESCRIPTION
        "The value of the object tmnxCallTraceLocationDisable specifies
         whether the given compact flash card shall be used as the local
         storage for the generated log files or not.

         The value 'true(1)' means the local storage on the given compact flash
         card is disabled and no files will be created on it.

         The value 'false(2)' means the local storage on the given compact flash
         card is enabled and files and can be created on it."
    DEFVAL { false }
    ::= { tmnxCallTraceLocationEntry 4 }

tmnxCallTraceLocationStatsTable OBJECT-TYPE
    SYNTAX      SEQUENCE OF TmnxCallTraceLocationStatsEntry
    MAX-ACCESS  not-accessible
    STATUS      current
    DESCRIPTION
        "The table tmnxCallTraceLocationStatsTable contains information
         pertaining to the state of the local storage of call trace
         log files on the compact flash cards.

         In release 14.0 only cf1 and cf2 can be used as the local
         storage of call trace log files."
    ::= { tmnxCallTraceConfigObjs 3 }

tmnxCallTraceLocationStatsEntry OBJECT-TYPE
    SYNTAX      TmnxCallTraceLocationStatsEntry
    MAX-ACCESS  not-accessible
    STATUS      current
    DESCRIPTION
        "Each row entry represents one compact flash card to be used for local
         storage of call trace log files.

         Rows in the table tmnxCallTraceLocationTable are created
         by the SYSTEM at its startup and are never destroyed."
    AUGMENTS { tmnxCallTraceLocationEntry }
    ::= { tmnxCallTraceLocationStatsTable 1 }

TmnxCallTraceLocationStatsEntry ::= SEQUENCE {
        tmnxCallTraceLocationUsedSpace  Unsigned32,
        tmnxCallTraceLocationAvailSpace Unsigned32
    }

tmnxCallTraceLocationUsedSpace OBJECT-TYPE
    SYNTAX      Unsigned32
    UNITS       "megabytes"
    MAX-ACCESS  read-only
    STATUS      current
    DESCRIPTION
        "The value of the object tmnxCallTraceLocationUsedSpace indicates
         the amount of used storage space in megabytes on the CF card."
    ::= { tmnxCallTraceLocationStatsEntry 1 }

tmnxCallTraceLocationAvailSpace OBJECT-TYPE
    SYNTAX      Unsigned32
    UNITS       "megabytes"
    MAX-ACCESS  read-only
    STATUS      current
    DESCRIPTION
        "The value of the object tmnxCallTraceLocationAvailSpace indicates
         the amount of available storage space in megabytes on the CF card."
    ::= { tmnxCallTraceLocationStatsEntry 2 }

-- ==========================================================================
-- Read-only TABLES
-- ==========================================================================
tmnxCallTraceStatsObjs  OBJECT IDENTIFIER ::= { tmnxCallTraceObjs 3 }

-- --------------------------------------------------------------------------
-- Call trace jobs related objects
-- --------------------------------------------------------------------------
tmnxCallTraceJobTable  OBJECT-TYPE
    SYNTAX      SEQUENCE OF TmnxCallTraceJobEntry
    MAX-ACCESS  not-accessible
    STATUS      current
    DESCRIPTION
        "The table tmnxCallTraceJobTable contains read-only information
         pertaining to all call trace jobs present in the system."
    ::= { tmnxCallTraceStatsObjs 1 }

tmnxCallTraceJobEntry  OBJECT-TYPE
    SYNTAX      TmnxCallTraceJobEntry
    MAX-ACCESS  not-accessible
    STATUS      current
    DESCRIPTION
        "Each row entry represents a call trace job existing in the system.

         Rows in the table tmnxCallTraceProfileTable are automatically created
         by the system at creation of a call trace job and destroyed
         at removal of the job from the system."
    INDEX { tmnxCallTraceJobId }
    ::= { tmnxCallTraceJobTable 1 }

TmnxCallTraceJobEntry ::= SEQUENCE {
        tmnxCallTraceJobId                Unsigned32,
        tmnxCallTraceJobType              TmnxCallTraceHostType,
        tmnxCallTraceJobWlanGwUeIeeeAddr  MacAddress,
        tmnxCallTraceJobStatus            TmnxCallTraceJobStatus,
        tmnxCallTraceJobProfileName       TNamedItem,
        tmnxCallTraceJobSizeLimit         TmnxCallTraceSizeLimit,
        tmnxCallTraceJobTimeLimit         TmnxCallTraceTimeLimit,
        tmnxCallTraceJobCaptureFormat     INTEGER,
        tmnxCallTraceJobDstAddrType       InetAddressType,
        tmnxCallTraceJobDstAddr           InetAddress,
        tmnxCallTraceJobDstResAddrType    InetAddressType,
        tmnxCallTraceJobDstResAddr        InetAddress,
        tmnxCallTraceJobDstPort           InetPortNumber,
        tmnxCallTraceJobVRtrId            TmnxVRtrID,
        tmnxCallTraceJobStartTime         DateAndTime,
        tmnxCallTraceJobCaptMsgsCnt       Unsigned32,
        tmnxCallTraceJobCaptMsgsSize      Unsigned32
    }

tmnxCallTraceJobId OBJECT-TYPE
    SYNTAX      Unsigned32 (0..254)
    MAX-ACCESS  not-accessible
    STATUS      current
    DESCRIPTION
        "The value of the object tmnxCallTraceJobId indicates the ID
         of the call trace job."
    ::= { tmnxCallTraceJobEntry 1 }

tmnxCallTraceJobType OBJECT-TYPE
    SYNTAX      TmnxCallTraceHostType
    MAX-ACCESS  read-only
    STATUS      current
    DESCRIPTION
        "The value of the object tmnxCallTraceJobType indicates the type
         of the call trace job.

         If the value is 'ue(1)' then the IEEE address of the UE being monitored
         is indicated by tmnxCallTraceJobWlanGwUeIeeeAddr.
         "
    ::= { tmnxCallTraceJobEntry 2 }

tmnxCallTraceJobWlanGwUeIeeeAddr OBJECT-TYPE
    SYNTAX      MacAddress
    MAX-ACCESS  read-only
    STATUS      current
    DESCRIPTION
        "The value of the object tmnxCallTraceJobWlanGwUeIeeeAddr indicates
         the IEEE address of the UE being monitored by this call trace job.

         The value is only valid when the value of the object
         tmnxCallTraceJobType is 'ue(1)'."
    ::= { tmnxCallTraceJobEntry 3 }

tmnxCallTraceJobStatus OBJECT-TYPE
    SYNTAX      TmnxCallTraceJobStatus
    MAX-ACCESS  read-only
    STATUS      current
    DESCRIPTION
        "The value of the object tmnxCallTraceJobStatus indicates
         the status of the call trace job.

         The value 'running (0)' indicates the job is active and is tracing
         events triggered by the host.

         If the value of the tmnxCallTraceJobType is 'ue(1)' then the host to
         trace is specified by the value of the tmnxCallTraceJobWlanGwUeIeeeAddr
         object.


         The value 'finished (1)' indicates the job has already finished
         and is not tracing events generated by the host anymore. The job was
         terminated either due to reaching one of the defined limits
         (tmnxCallTraceJobSizeLimit or tmnxCallTraceJobTimeLimit)
         or manual intervention of an operator."
    ::= { tmnxCallTraceJobEntry 4 }

tmnxCallTraceJobProfileName OBJECT-TYPE
    SYNTAX      TNamedItem
    MAX-ACCESS  read-only
    STATUS      current
    DESCRIPTION
        "The value of the object tmnxCallTraceJobProfileName indicates
         the name of the call trace profile used to define job's parameters
         at the moment of creation of the job.

         Note: Current values of the trace profile's parameters
         in tmnxCallTraceProfileTable may differ from their values
         at the moment of creation of the job."
    ::= { tmnxCallTraceJobEntry 5 }

tmnxCallTraceJobSizeLimit OBJECT-TYPE
    SYNTAX      TmnxCallTraceSizeLimit
    UNITS       "megabytes"
    MAX-ACCESS  read-only
    STATUS      current
    DESCRIPTION
        "The value of the object tmnxCallTraceJobSizeLimit indicates
         the maximum data volume generated by this call trace job
         to an output in megabytes.

         If the value of the object tmnxCallTraceJobStatus is 'running (0)'
         then the job will be automatically terminated after reaching
         this limit."
    ::= { tmnxCallTraceJobEntry 6 }

tmnxCallTraceJobTimeLimit OBJECT-TYPE
    SYNTAX      TmnxCallTraceTimeLimit
    UNITS       "sec"
    MAX-ACCESS  read-only
    STATUS      current
    DESCRIPTION
        "The value of the object tmnxCallTraceJobTimeLimit indicates
         the maximum duration of this call trace job in seconds.

         If the value of the object tmnxCallTraceJobStatus is 'running (0)'
         then the job will be automatically terminated after reaching
         this limit."
    ::= { tmnxCallTraceJobEntry 7 }

tmnxCallTraceJobCaptureFormat OBJECT-TYPE
    SYNTAX      INTEGER {
                         pcap(1)
                        }
    MAX-ACCESS  read-only
    STATUS      current
    DESCRIPTION
        "The value of the object tmnxCallTraceJobCaptureFormat indicates
         the format in which the logs generated by this call trace job
         are stored on cflash cards and sent to the live output defined
         by the values of the objects tmnxCallTraceJobDstAddrType,
         tmnxCallTraceJobDstAddr, tmnxCallTraceJobDstPort
         and tmnxCallTraceJobVRtrId."
    ::= { tmnxCallTraceJobEntry 8 }

tmnxCallTraceJobDstAddrType OBJECT-TYPE
    SYNTAX      InetAddressType
    MAX-ACCESS  read-only
    STATUS      current
    DESCRIPTION
        "The value of the object tmnxCallTraceJobDstAddrType indicates
         the context (IP address type or Fully Qualified Domain Name (FQDN))
         in which the value of the object tmnxCallTraceJobDstAddr
         is to be interpreted.

         Only values 'unknown (0)', 'ipv4 (1)', 'ipv6 (2)' and 'dns (16)'
         are supported."
    ::= { tmnxCallTraceJobEntry 9 }

tmnxCallTraceJobDstAddr OBJECT-TYPE
    SYNTAX      InetAddress (SIZE (0..255))
    MAX-ACCESS  read-only
    STATUS      current
    DESCRIPTION
        "The value of the object tmnxCallTraceJobDstAddr indicates
         the live output destination address of the trace log generated
         by this call trace job.

         This object can contain a non-empty value only if the value
         of the object tmnxCallTraceJobDstAddrType is other than 'unknown (0)'.

         In that case the live output is being sent to the destination
         identified by the IP address / FQDN value of this object
         and the values of the objects tmnxCallTraceJobDstPort
         and tmnxCallTraceJobVRtrId.

         If the value of this object holds FQDN then the resolved IP address
         is indicated by the value of tmnxCallTraceJobDstResAddr.

         If the value of this object is empty then a local compact flash card
         is used as the destination.

         If the value of the object tmnxCallTraceJobDstAddrType is
         'unknown (0)' then the size of this object can be only 0.

         If the value of the object tmnxCallTraceJobDstAddrType is
         'ipv4(1)' then the size of this object can be only 4.

         If the value of the object tmnxCallTraceJobDstAddrType is
         'ipv6(2)' then the size of this object can be only 16.

         If the value of the object tmnxCallTraceJobDstAddrType is
         'dns(16)' then the size of this object can be 1..255."
    ::= { tmnxCallTraceJobEntry 10 }

tmnxCallTraceJobDstResAddrType OBJECT-TYPE
    SYNTAX      InetAddressType
    MAX-ACCESS  read-only
    STATUS      current
    DESCRIPTION
        "The value of the object tmnxCallTraceJobDstResAddrType indicates the
         context, in which the value of the object tmnxCallTraceJobDstResAddr
         is to be interpreted.

         Only values 'unknown (0)', 'ipv4 (1)' and 'ipv6 (2)' are supported.

         This object can hold value other than 'unknown (0)' only if the value
         of the object tmnxCallTraceJobDstAddrType is 'dns (16)'."
    ::= { tmnxCallTraceJobEntry 11 }

tmnxCallTraceJobDstResAddr OBJECT-TYPE
    SYNTAX      InetAddress (SIZE (0|4|16))
    MAX-ACCESS  read-only
    STATUS      current
    DESCRIPTION
        "The value of the object tmnxCallTraceJobDstResAddr indicates
         the IP address, that the FQDN indicated by the value of
         tmnxCallTraceJobDstAddr was resolved into.

         This object can contain a non-empty value only if the value
         of the object tmnxCallTraceJobDstResAddrType is other than
         'unknown (0)'."
    ::= { tmnxCallTraceJobEntry 12 }

tmnxCallTraceJobDstPort OBJECT-TYPE
    SYNTAX      InetPortNumber (1..65535)
    MAX-ACCESS  read-only
    STATUS      current
    DESCRIPTION
        "The value of the object tmnxCallTraceJobDstPort indicates
         the destination UDP port on the destination indicated by the value
         of the object tmnxCallTraceJobDstAddr which the live output generated
         by this call trace job is being sent to.

         The value of this object shall be ignored if the value of the object
         tmnxCallTraceJobDstAddr is equal to 'unknown (0)'."
    ::= { tmnxCallTraceJobEntry 13 }

tmnxCallTraceJobVRtrId OBJECT-TYPE
    SYNTAX      TmnxVRtrID
    MAX-ACCESS  read-only
    STATUS      current
    DESCRIPTION
        "The value of the object tmnxCallTraceJobVRtrId indicates
         the virtual router instance ID in scope of which the live output
         destination identified by the values of the objects
         tmnxCallTraceJobDstAddr and tmnxCallTraceJobDstPort
         is to be reached.

         The value '1' identifies the 'Base' router instance.

         The value of this object shall be ignored if the value of the object
         tmnxCallTraceJobDstAddr is equal to 'unknown (0)'."
    ::= { tmnxCallTraceJobEntry 14 }

tmnxCallTraceJobStartTime OBJECT-TYPE
    SYNTAX      DateAndTime
    MAX-ACCESS  read-only
    STATUS      current
    DESCRIPTION
        "The value of the object tmnxCallTraceJobStartTime indicates
         the time when this call trace job has been started."
    ::= { tmnxCallTraceJobEntry 15 }

tmnxCallTraceJobCaptMsgsCnt OBJECT-TYPE
    SYNTAX      Unsigned32
    MAX-ACCESS  read-only
    STATUS      current
    DESCRIPTION
        "The value of the object tmnxCallTraceJobCaptMsgsCnt indicates
         the number of events this call trace job has generated so far."
    ::= { tmnxCallTraceJobEntry 16 }

tmnxCallTraceJobCaptMsgsSize OBJECT-TYPE
    SYNTAX      Unsigned32
    MAX-ACCESS  read-only
    STATUS      current
    DESCRIPTION
        "The value of the object tmnxCallTraceJobCaptMsgsSize indicates
         the total size of all messages this call trace job has generated
         so far."
    ::= { tmnxCallTraceJobEntry 17 }

-- --------------------------------------------------------------------------
-- Call trace files related objects
-- --------------------------------------------------------------------------
tmnxCallTraceFileTable  OBJECT-TYPE
    SYNTAX      SEQUENCE OF TmnxCallTraceFileEntry
    MAX-ACCESS  not-accessible
    STATUS      current
    DESCRIPTION
        "The table tmnxCallTraceFileTable contains read-only information
         pertaining to all call trace log files locally stored on cflash
         cards in the system.

         To limit the impact on the file system the contents of the table
         is refreshed on SNMP GET/NEXT request only if the previous update
         has been done more than 5 seconds ago (for active jobs)
         or 10 seconds ago (for finished jobs)."
    ::= { tmnxCallTraceStatsObjs 2 }

tmnxCallTraceFileEntry  OBJECT-TYPE
    SYNTAX      TmnxCallTraceFileEntry
    MAX-ACCESS  not-accessible
    STATUS      current
    DESCRIPTION
        "Each row entry represents a single call trace file present
         on a cflash card.

         Rows in the table tmnxCallTraceFileTable are automatically created
         by the system at creation of a call trace log file and destroyed
         at removal of the file from the cflash card."
    INDEX {
            tmnxCallTraceFileJobStatus,
            tmnxCallTraceFileCpmSlotNum,
            tmnxCallTraceFileCFlashId,
            tmnxCallTraceFileName
          }
    ::= { tmnxCallTraceFileTable 1 }

TmnxCallTraceFileEntry ::= SEQUENCE {
        tmnxCallTraceFileJobStatus      TmnxCallTraceJobStatus,
        tmnxCallTraceFileCpmSlotNum     TmnxSlotNum,
        tmnxCallTraceFileCFlashId       TmnxCallTraceCFlashId,
        tmnxCallTraceFileName           DisplayString,
        tmnxCallTraceFileDir            DisplayString,
        tmnxCallTraceFileSize           Unsigned32,
        tmnxCallTraceFileLastDataModif  DateAndTime
    }

tmnxCallTraceFileJobStatus OBJECT-TYPE
    SYNTAX      TmnxCallTraceJobStatus
    MAX-ACCESS  not-accessible
    STATUS      current
    DESCRIPTION
        "The value of the object tmnxCallTraceFileJobStatus indicates
         the status of the call trace job that has created this log file.

         The details about the call trace job can be found
         in tmnxCallTraceJobTable.

         The value 'running (0)' indicates the job is active and is tracing
         events triggered by the host and events are being recorded
         to the file.

         The value 'finished (1)' indicates the job has already finished
         and is not tracing events generated by the host anymore."
    ::= { tmnxCallTraceFileEntry 1 }

tmnxCallTraceFileCpmSlotNum OBJECT-TYPE
    SYNTAX      TmnxSlotNum
    MAX-ACCESS  not-accessible
    STATUS      current
    DESCRIPTION
        "The value of the object tmnxCallTraceFileCpmSlotNum indicates
         the CPM slot where the cflash card containing the log file
         is present."
    ::= { tmnxCallTraceFileEntry 2 }

tmnxCallTraceFileCFlashId OBJECT-TYPE
    SYNTAX      TmnxCallTraceCFlashId
    MAX-ACCESS  not-accessible
    STATUS      current
    DESCRIPTION
        "The value of the object tmnxCallTraceFileCFlashId indicates
         the ID of the cflash card on the CPM board identified by the value
         of the object tmnxCallTraceFileCpmSlotNum where the log file
         is present."
    ::= { tmnxCallTraceFileEntry 3 }

tmnxCallTraceFileName OBJECT-TYPE
    SYNTAX      DisplayString (SIZE (38..83))
    MAX-ACCESS  not-accessible
    STATUS      current
    DESCRIPTION
        "The value of the object tmnxCallTraceFileName indicates the basename
         of the log file.

         The basename is composed of following items:

            'mac_<mac_address>_<timestamp>[_<internal_id>].pcap'

             where

            <mac_address> is a MAC address of the host in form '00-11-22-33-44-55'
            <timestamp> is a date and time of creation of the file
                        in form 'YYMMDD_HHMM' (24 hr format)
            <internal_id> is a value used for internal purposes
            "
    ::= { tmnxCallTraceFileEntry 4 }

tmnxCallTraceFileDir OBJECT-TYPE
    SYNTAX      DisplayString (SIZE (18..19))
    MAX-ACCESS  read-only
    STATUS      current
    DESCRIPTION
        "The value of the object tmnxCallTraceFileDir indicates the absolute
         pathname of the directory where the log file identified by the value
         of the object tmnxCallTraceFileName is stored on the cflash card
         identified by the values of the objects tmnxCallTraceFileCpmSlotNum
         and tmnxCallTraceFileCFlashId.

         In release 14.0 the only possible locations are:
             '/calltrace/running'
             '/calltrace/finished'"
    ::= { tmnxCallTraceFileEntry 5 }

tmnxCallTraceFileSize OBJECT-TYPE
    SYNTAX      Unsigned32
    UNITS       "bytes"
    MAX-ACCESS  read-only
    STATUS      current
    DESCRIPTION
        "The value of the object tmnxCallTraceFileSize indicates the size
         of the log file in bytes."
    ::= { tmnxCallTraceFileEntry 6 }

tmnxCallTraceFileLastDataModif OBJECT-TYPE
    SYNTAX      DateAndTime
    MAX-ACCESS  read-only
    STATUS      current
    DESCRIPTION
        "The value of the object tmnxCallTraceFileLastDataModif indicates
         the time of the last modification to this file."
    ::= { tmnxCallTraceFileEntry 7 }

-- ==========================================================================
-- NOTIFICATIONS
-- ==========================================================================
tmnxCallTraceNotificationObjs OBJECT IDENTIFIER ::= { tmnxCallTraceObjs 20 }

--OBJECT-TYPEs that are only 'accessible-for-notify' first...

--NOTIFICATION-TYPE definitions next

tmnxCallTraceMaxFilesNumReached NOTIFICATION-TYPE
    OBJECTS {
        tmnxCallTraceMaxFilesNumber
    }
    STATUS      current
    DESCRIPTION
        "[CAUSE] This notification is triggered for the following reasons:

         1) Cumulative number of call trace log files present on all cflash
            cards on the active CPM that are being used for local storage
            has reached the limit defined by the value of the object
            tmnxCallTraceMaxFilesNumber.

         2) The value of the object tmnxCallTraceMaxFilesNumber has been changed
            to a value that is lower than the current cumulative number
            of all call trace log files present on all cflash cards
            on the active CPM that are being used for local storage.

         Details about cflash cards that are being used for the local storage
         of call trace log files can be found in tmnxCallTraceLocationTable.

         [EFFECT] New call trace log file(s) cannot be created on any
         cflash card.

         [RECOVERY] Operator may execute one of the following actions to restore
         the functionality:

         1) Remove some call trace log files from (a) cflash card(s).

         2) Increase the value of the object tmnxCallTraceMaxFilesNumber."
    ::= { tmnxCallTraceNotifications 1 }

tmnxCallTraceLocSizeLimitReached NOTIFICATION-TYPE
    OBJECTS {
        tmnxCallTraceLocationSizeLimit
    }
    STATUS      current
    DESCRIPTION
        "[CAUSE] This notification is triggered when the cumulative size of
         all call trace log files on a given cflash card on the active CPM
         has reached the limit specified by the value of the object
         tmnxCallTraceLocationSizeLimit.

         [EFFECT] New call trace log file(s) cannot be created on the impacted
         cflash card.

         [RECOVERY] Operator may execute one of the following actions to restore
         the functionality:

         1) Remove some call trace log files from the cflash card.

         2) Increase the size limit (value of the object
         tmnxCallTraceLocationSizeLimit) for the given cflash card."
    ::= { tmnxCallTraceNotifications 2 }

-- ==========================================================================
--  COMPLIANCE STATEMENTS
-- ==========================================================================
tmnxCallTraceCompliance              MODULE-COMPLIANCE
    STATUS      current
    DESCRIPTION
        "The compliance statement for the management of call trace feature
         on Nokia SROS series systems."
    MODULE -- this module
        MANDATORY-GROUPS {
            tmnxCallTraceProfileGroup,
            tmnxCallTraceLocStoreGroup,
            tmnxCallTraceScalarCfgGroup,
            tmnxCallTraceJobGroup,
            tmnxCallTraceNotifyGroup,
            tmnxCallTraceFileGroup,
            tmnxCallTraceScalarStatsGroup
        }
    ::= { tmnxCallTraceCompliances 1 }

-- ==========================================================================
-- OBJECT-GROUPS/NOTIFICATION-GROUPS
-- ==========================================================================
tmnxCallTraceInitialGroups      OBJECT IDENTIFIER ::= { tmnxCallTraceGroups 1 }

tmnxCallTraceProfileGroup OBJECT-GROUP
    OBJECTS {
        tmnxCallTraceProfileTblLstChgd,
        tmnxCallTraceProfileLstChgd,
        tmnxCallTraceProfileRowStatus,
        tmnxCallTraceProfileDescription,
        tmnxCallTraceProfileSizeLimit,
        tmnxCallTraceProfileTimeLimit,
        tmnxCallTraceProfileDstAddrType,
        tmnxCallTraceProfileDstAddr,
        tmnxCallTraceProfileDstPort,
        tmnxCallTraceProfileVRtrId,
        tmnxCallTraceProfileDbgOutput
    }
    STATUS current
    DESCRIPTION
        "The group of objects supporting the management of call trace
         profiles on Nokia SROS systems."
    ::= { tmnxCallTraceInitialGroups 1 }

tmnxCallTraceLocStoreGroup OBJECT-GROUP
    OBJECTS {
        tmnxCallTraceLocationTblLstChgd,
        tmnxCallTraceLocationLstChgd,
        tmnxCallTraceLocationSizeLimit,
        tmnxCallTraceLocationDisable,
        tmnxCallTraceLocationUsedSpace,
        tmnxCallTraceLocationAvailSpace
    }
    STATUS current
    DESCRIPTION
        "The group of objects supporting the management of call trace
         local storage on Nokia SROS systems."
    ::= { tmnxCallTraceInitialGroups 2 }

tmnxCallTraceScalarCfgGroup OBJECT-GROUP
    OBJECTS {
        tmnxCallTraceMaxFilesNumber,
        tmnxCallTracePrimaryCFlash
    }
    STATUS current
    DESCRIPTION
        "The group of objects supporting the management of call trace
         scalar configuration on Nokia SROS systems."
    ::= { tmnxCallTraceInitialGroups 3 }

tmnxCallTraceJobGroup OBJECT-GROUP
    OBJECTS {
        tmnxCallTraceJobType,
        tmnxCallTraceJobWlanGwUeIeeeAddr,
        tmnxCallTraceJobStatus,
        tmnxCallTraceJobProfileName,
        tmnxCallTraceJobSizeLimit,
        tmnxCallTraceJobTimeLimit,
        tmnxCallTraceJobCaptureFormat,
        tmnxCallTraceJobDstAddrType,
        tmnxCallTraceJobDstAddr,
        tmnxCallTraceJobDstResAddrType,
        tmnxCallTraceJobDstResAddr,
        tmnxCallTraceJobDstPort,
        tmnxCallTraceJobVRtrId,
        tmnxCallTraceJobStartTime,
        tmnxCallTraceJobCaptMsgsCnt,
        tmnxCallTraceJobCaptMsgsSize
    }
    STATUS current
    DESCRIPTION
        "The group of objects supporting the presenatation of call trace
         job related data on Nokia SROS systems."
    ::= { tmnxCallTraceInitialGroups 4 }

tmnxCallTraceNotifyGroup NOTIFICATION-GROUP
    NOTIFICATIONS {
        tmnxCallTraceMaxFilesNumReached,
        tmnxCallTraceLocSizeLimitReached
    }
    STATUS current
    DESCRIPTION
        "The group of notifications supporting call trace
         feature on Nokia SROS systems."
    ::= { tmnxCallTraceInitialGroups 5 }

tmnxCallTraceFileGroup OBJECT-GROUP
    OBJECTS {
        tmnxCallTraceFileDir,
        tmnxCallTraceFileSize,
        tmnxCallTraceFileLastDataModif
    }
    STATUS current
    DESCRIPTION
        "The group of objects supporting the presenatation of call trace
         files related data for Nokia SROS systems."
    ::= { tmnxCallTraceInitialGroups 6 }

tmnxCallTraceScalarStatsGroup OBJECT-GROUP
    OBJECTS {
        tmnxCallTraceUsedFilesNumber,
        tmnxCallTraceAvailFilesNumber
    }
    STATUS current
    DESCRIPTION
        "The group of objects supporting the management of call trace
         scalar configuration on Nokia SROS systems."
    ::= { tmnxCallTraceInitialGroups 7 }


END
